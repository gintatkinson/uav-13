doc /* Consolidated Level 0 OEM Specifications */
package extracted {
    doc /* [unit: m/s] */
    attribute PL_01 : Real;
    doc /* [unit: m/s] */
    attribute PL_02 : Real;
    doc /* [unit: m/s] */
    attribute PL_03 : Real;
    doc /* [unit: deg] */
    attribute PL_04 : Real;
    doc /* [unit: m/s] */
    attribute PL_05 : Real;
    doc /* [unit: min] */
    attribute PL_06 : Real;
    doc /* [unit: km] */
    attribute PL_07 : Real;
    doc /* [unit: km] */
    attribute PL_08 : Real;
    doc /* [unit: m] */
    attribute PL_09 : Real;
    doc /* [unit: m] */
    attribute PL_10 : Real;
    doc /* [unit: m] */
    attribute PL_11 : Real;
    doc /* [unit: kg] */
    attribute PL_12 : Real;
    doc /* [unit: kg] */
    attribute PL_13 : Real;
    doc /* [unit: units] */
    attribute PL_14 : Real;
    doc /* [unit: units] */
    attribute PL_15 : Real;
    doc /* [unit: units] */
    attribute PL_16 : Real;
    doc /* [unit: units] */
    attribute PL_17 : Real;
    doc /* [unit: units] */
    attribute PL_18 : Real;
    doc /* [unit: cm] */
    attribute PL_19 : Real;
    doc /* [unit: cm] */
    attribute PL_20 : Real;
    doc /* [unit: cm] */
    attribute PL_21 : Real;
    doc /* [unit: V] */
    attribute PL_22 : Real;
    doc /* [unit: V] */
    attribute PL_23 : Real;
    doc /* [unit: V] */
    attribute PL_24 : Real;
    doc /* [unit: deg] */
    attribute PL_25 : Real;
    doc /* [unit: deg] */
    attribute PL_26 : Real;
    doc /* [unit: X] */
    attribute PL_27 : Real;
    doc /* [unit: pixels] */
    attribute PL_28 : Real;
    doc /* [unit: pixels] */
    attribute PL_29 : Real;
    doc /* [unit: pixels] */
    attribute PL_30 : Real;
    doc /* [unit: pixels] */
    attribute PL_31 : Real;
    doc /* [unit: V] */
    attribute PL_32 : Real;
    doc /* [unit: V] */
    attribute PL_33 : Real;
    doc /* [unit: m/s] */
    attribute PL_34 : Real;
    doc /* [unit: m/s] */
    attribute PL_35 : Real;
    doc /* [unit: m] */
    attribute PL_36 : Real;
    doc /* [unit: m] */
    attribute PL_37 : Real;
    doc /* [unit: chars] */
    attribute PL_38 : Real;
    doc /* [unit: W] */
    attribute PL_39 : Real;
    doc /* [unit: bar] */
    attribute PL_40 : Real;
    doc /* [unit: bar] */
    attribute PL_41 : Real;
    doc /* [unit: s] */
    attribute PL_42 : Real;
    doc /* [unit: s] */
    attribute PL_43 : Real;
    doc /* [unit: deg] */
    attribute PL_44 : Real;
    doc /* [unit: m/s] */
    attribute PL_45 : Real;
    doc /* [unit: V] */
    attribute PL_46 : Real;
    doc /* [unit: V] */
    attribute PL_47 : Real;
    doc /* [unit: V] */
    attribute PL_48 : Real;
    doc /* [unit: Ohm] */
    attribute PL_49 : Real;
    doc /* [unit: mA] */
    attribute PL_50 : Real;
    doc /* [unit: VDC] */
    attribute PL_51 : Real;
    doc /* [unit: VDC] */
    attribute PL_52 : Real;
    doc /* [unit: VDC] */
    attribute PL_53 : Real;
    doc /* [unit: ms] */
    attribute PL_54 : Real;
    doc /* [unit: percent] */
    attribute PL_55 : Real;
    doc /* [unit: bps] */
    attribute PL_56 : Real;
    doc /* [unit: Hz] */
    attribute PL_57 : Real;
    doc /* [unit: ms] */
    attribute PL_58 : Real;
    doc /* [unit: ms] */
    attribute PL_59 : Real;
    doc /* [unit: V] */
    attribute PL_60 : Real;
    doc /* [unit: bytes] */
    attribute PL_61 : Real;
    doc /* [unit: bytes] */
    attribute PL_62 : Real;
    doc /* [unit: g] */
    attribute PL_63 : Real;
    doc /* [unit: kg] */
    attribute PL_64 : Real;
    doc /* [unit: m/s] */
    attribute PL_65 : Real;
    doc /* [unit: deg] */
    attribute PL_66 : Real;
    doc /* [unit: bar] */
    attribute PL_67 : Real;
    doc /* [unit: bar] */
    attribute PL_68 : Real;
    doc /* [unit: kg] */
    attribute PL_69 : Real;
    doc /* [unit: kg] */
    attribute PL_70 : Real;
    doc /* [unit: kg] */
    attribute PL_71 : Real;
    doc /* [unit: min] */
    attribute PL_72 : Real;
    doc /* [unit: degC] */
    attribute PL_73 : Real;
    doc /* [unit: degC] */
    attribute PL_74 : Real;
    doc /* [unit: V] */
    attribute PL_75 : Real;
    doc /* [unit: mAh] */
    attribute PL_76 : Real;
    doc /* [unit: V] */
    attribute PL_77 : Real;
    doc /* [unit: V] */
    attribute PL_78 : Real;
    doc /* [unit: s] */
    attribute PL_79 : Real;
    doc /* [unit: launches] */
    attribute PL_80 : Real;
    doc /* [unit: mm] */
    attribute PL_81 : Real;
    doc /* [unit: mm] */
    attribute PL_82 : Real;
    doc /* [unit: mm] */
    attribute PL_83 : Real;
    doc /* [unit: mm] */
    attribute PL_84 : Real;
    doc /* [unit: mm] */
    attribute PL_85 : Real;
    doc /* [unit: mm] */
    attribute PL_86 : Real;
    doc /* [unit: mm] */
    attribute PL_87 : Real;
    doc /* [unit: s] */
    attribute PL_88 : Real;
    doc /* [unit: min] */
    attribute PL_89 : Real;
    doc /* [unit: min] */
    attribute PL_90 : Real;
    doc /* [unit: degC] */
    attribute PL_91 : Real;
    doc /* [unit: degC] */
    attribute PL_92 : Real;
    doc /* [unit: m] */
    attribute PL_93 : Real;
    doc /* [unit: m] */
    attribute PL_94 : Real;
    doc /* [Source: avenger_v2_5_sysml_v2_ingestion.md:72, avenger_v2_5_sysml_v2_ingestion.md:171] */
    port inout CAN_1_Trunk_970_cm : CAN_frame {
        attribute protocol_family : String = "CAN bus DroneCAN";
    }
    doc /* [Source: avenger_v2_5_sysml_v2_ingestion.md:73] */
    port inout CAN_1_EPS_Tap : CAN_frame {
        attribute protocol_family : String = "CAN bus DroneCAN";
    }
    doc /* [Source: avenger_v2_5_sysml_v2_ingestion.md:74, avenger_v2_5_sysml_v2_ingestion.md:172] */
    port inout CAN_1_Branch_150_cm : CAN_frame {
        attribute protocol_family : String = "CAN bus DroneCAN";
    }
    doc /* [Source: avenger_v2_5_sysml_v2_ingestion.md:75, avenger_v2_5_sysml_v2_ingestion.md:173] */
    port inout CAN_1_Ruddervator_Servo_1_Branch_120_cm : Servo_command_and_status_frame {
        attribute protocol_family : String = "CAN bus DroneCAN";
    }
    doc /* [Source: avenger_v2_5_sysml_v2_ingestion.md:76, avenger_v2_5_sysml_v2_ingestion.md:173] */
    port inout CAN_1_Ruddervator_Servo_2_Branch_120_cm : Servo_command_and_status_frame {
        attribute protocol_family : String = "CAN bus DroneCAN";
    }
    doc /* [Source: avenger_v2_5_sysml_v2_ingestion.md:77, avenger_v2_5_sysml_v2_ingestion.md:173] */
    port inout CAN_1_Ruddervator_Servo_3_Branch_120_cm : Servo_command_and_status_frame {
        attribute protocol_family : String = "CAN bus DroneCAN";
    }
    doc /* [Source: avenger_v2_5_sysml_v2_ingestion.md:78, avenger_v2_5_sysml_v2_ingestion.md:173] */
    port inout CAN_1_Ruddervator_Servo_4_Branch_120_cm : Servo_command_and_status_frame {
        attribute protocol_family : String = "CAN bus DroneCAN";
    }
    doc /* [Source: avenger_v2_5_sysml_v2_ingestion.md:79, avenger_v2_5_sysml_v2_ingestion.md:155] */
    port out Servo_Power_8V_Ruddervator_Servo_1 : _8_V_DC {
        attribute protocol_family : String = "DC power";
        doc /* [Source: avenger_v2_5_sysml_v2_ingestion.md:79, avenger_v2_5_sysml_v2_ingestion.md:155] */
        flow out Servo_Power_8V_Ruddervator_Servo_1_flow : _8_V_DC;
    }
    doc /* [Source: avenger_v2_5_sysml_v2_ingestion.md:80, avenger_v2_5_sysml_v2_ingestion.md:155] */
    port out Servo_Power_8V_Ruddervator_Servo_2 : _8_V_DC {
        attribute protocol_family : String = "DC power";
        doc /* [Source: avenger_v2_5_sysml_v2_ingestion.md:80, avenger_v2_5_sysml_v2_ingestion.md:155] */
        flow out Servo_Power_8V_Ruddervator_Servo_2_flow : _8_V_DC;
    }
    doc /* [Source: avenger_v2_5_sysml_v2_ingestion.md:81, avenger_v2_5_sysml_v2_ingestion.md:155] */
    port out Servo_Power_8V_Ruddervator_Servo_3 : _8_V_DC {
        attribute protocol_family : String = "DC power";
        doc /* [Source: avenger_v2_5_sysml_v2_ingestion.md:81, avenger_v2_5_sysml_v2_ingestion.md:155] */
        flow out Servo_Power_8V_Ruddervator_Servo_3_flow : _8_V_DC;
    }
    doc /* [Source: avenger_v2_5_sysml_v2_ingestion.md:82, avenger_v2_5_sysml_v2_ingestion.md:155] */
    port out Servo_Power_8V_Ruddervator_Servo_4 : _8_V_DC {
        attribute protocol_family : String = "DC power";
        doc /* [Source: avenger_v2_5_sysml_v2_ingestion.md:82, avenger_v2_5_sysml_v2_ingestion.md:155] */
        flow out Servo_Power_8V_Ruddervator_Servo_4_flow : _8_V_DC;
    }
    doc /* [Source: avenger_v2_5_sysml_v2_ingestion.md:83, avenger_v2_5_sysml_v2_ingestion.md:157] */
    port out Servo_Power_8V_Splitter_Input_1 : _8_V_DC {
        attribute protocol_family : String = "DC power";
        doc /* [Source: avenger_v2_5_sysml_v2_ingestion.md:83, avenger_v2_5_sysml_v2_ingestion.md:157] */
        flow out Servo_Power_8V_Splitter_Input_1_flow : _8_V_DC;
    }
    doc /* [Source: avenger_v2_5_sysml_v2_ingestion.md:84, avenger_v2_5_sysml_v2_ingestion.md:157] */
    port out Servo_Power_8V_Splitter_Input_2 : _8_V_DC {
        attribute protocol_family : String = "DC power";
        doc /* [Source: avenger_v2_5_sysml_v2_ingestion.md:84, avenger_v2_5_sysml_v2_ingestion.md:157] */
        flow out Servo_Power_8V_Splitter_Input_2_flow : _8_V_DC;
    }
    doc /* [Source: avenger_v2_5_sysml_v2_ingestion.md:85, avenger_v2_5_sysml_v2_ingestion.md:157] */
    port out Servo_Power_8V_Splitter_Input_3 : _8_V_DC {
        attribute protocol_family : String = "DC power";
        doc /* [Source: avenger_v2_5_sysml_v2_ingestion.md:85, avenger_v2_5_sysml_v2_ingestion.md:157] */
        flow out Servo_Power_8V_Splitter_Input_3_flow : _8_V_DC;
    }
    doc /* [Source: avenger_v2_5_sysml_v2_ingestion.md:86, avenger_v2_5_sysml_v2_ingestion.md:157] */
    port out Servo_Power_8V_Splitter_Input_4 : _8_V_DC {
        attribute protocol_family : String = "DC power";
        doc /* [Source: avenger_v2_5_sysml_v2_ingestion.md:86, avenger_v2_5_sysml_v2_ingestion.md:157] */
        flow out Servo_Power_8V_Splitter_Input_4_flow : _8_V_DC;
    }
    doc /* [Source: avenger_v2_5_sysml_v2_ingestion.md:87, avenger_v2_5_sysml_v2_ingestion.md:156] */
    port out Servo_Power_8V_Wing_Servo_5 : _8_V_DC {
        attribute protocol_family : String = "DC power";
        doc /* [Source: avenger_v2_5_sysml_v2_ingestion.md:87, avenger_v2_5_sysml_v2_ingestion.md:156] */
        flow out Servo_Power_8V_Wing_Servo_5_flow : _8_V_DC;
    }
    doc /* [Source: avenger_v2_5_sysml_v2_ingestion.md:88, avenger_v2_5_sysml_v2_ingestion.md:156] */
    port out Servo_Power_8V_Wing_Servo_6 : _8_V_DC {
        attribute protocol_family : String = "DC power";
        doc /* [Source: avenger_v2_5_sysml_v2_ingestion.md:88, avenger_v2_5_sysml_v2_ingestion.md:156] */
        flow out Servo_Power_8V_Wing_Servo_6_flow : _8_V_DC;
    }
    doc /* [Source: avenger_v2_5_sysml_v2_ingestion.md:89, avenger_v2_5_sysml_v2_ingestion.md:156] */
    port out Servo_Power_8V_Wing_Servo_7 : _8_V_DC {
        attribute protocol_family : String = "DC power";
        doc /* [Source: avenger_v2_5_sysml_v2_ingestion.md:89, avenger_v2_5_sysml_v2_ingestion.md:156] */
        flow out Servo_Power_8V_Wing_Servo_7_flow : _8_V_DC;
    }
    doc /* [Source: avenger_v2_5_sysml_v2_ingestion.md:90, avenger_v2_5_sysml_v2_ingestion.md:156] */
    port out Servo_Power_8V_Wing_Servo_8 : _8_V_DC {
        attribute protocol_family : String = "DC power";
        doc /* [Source: avenger_v2_5_sysml_v2_ingestion.md:90, avenger_v2_5_sysml_v2_ingestion.md:156] */
        flow out Servo_Power_8V_Wing_Servo_8_flow : _8_V_DC;
    }
    doc /* [Source: avenger_v2_5_sysml_v2_ingestion.md:91, avenger_v2_5_sysml_v2_ingestion.md:157] */
    port out CAN_2_Splitter_Input : CAN_frame {
        attribute protocol_family : String = "CAN bus DroneCAN";
        doc /* [Source: avenger_v2_5_sysml_v2_ingestion.md:91, avenger_v2_5_sysml_v2_ingestion.md:157] */
        flow out CAN_2_Splitter_Input_flow : CAN_frame;
    }
    doc /* [Source: avenger_v2_5_sysml_v2_ingestion.md:92, avenger_v2_5_sysml_v2_ingestion.md:99] */
    port inout CAN_2_Daisy_Chain_Segment_5_to_6 : Servo_command_and_status_frame {
        attribute protocol_family : String = "CAN bus DroneCAN";
    }
    doc /* [Source: avenger_v2_5_sysml_v2_ingestion.md:99, avenger_v2_5_sysml_v2_ingestion.md:103] */
    port inout CAN_2_Daisy_Chain_Segment_6_to_7 : Servo_command_and_status_frame {
        attribute protocol_family : String = "CAN bus DroneCAN";
    }
    doc /* [Source: avenger_v2_5_sysml_v2_ingestion.md:103, avenger_v2_5_sysml_v2_ingestion.md:105] */
    port inout CAN_2_Daisy_Chain_Segment_7_to_8 : Servo_command_and_status_frame {
        attribute protocol_family : String = "CAN bus DroneCAN";
    }
    doc /* [Source: avenger_v2_5_sysml_v2_ingestion.md:106, avenger_v2_5_sysml_v2_ingestion.md:108] */
    port inout CAN_2_Magnetometer_Continuation : Sensor_frame {
        attribute protocol_family : String = "CAN bus DroneCAN";
    }
    doc /* [Source: avenger_v2_5_sysml_v2_ingestion.md:114, avenger_v2_5_sysml_v2_ingestion.md:122] */
    port inout ETH_Backbone : IP_packet {
        attribute protocol_family : String = "Ethernet";
    }
    doc /* [Source: avenger_v2_5_sysml_v2_ingestion.md:114] */
    port inout Camera_Module_ETH : IP_packet {
        attribute protocol_family : String = "Ethernet";
    }
    doc /* [Source: avenger_v2_5_sysml_v2_ingestion.md:118] */
    port inout RPI_ETH : IP_packet {
        attribute protocol_family : String = "Ethernet";
    }
    doc /* [Source: avenger_v2_5_sysml_v2_ingestion.md:116] */
    port inout External_ETH : IP_packet {
        attribute protocol_family : String = "Ethernet";
    }
    doc /* [Source: avenger_v2_5_sysml_v2_ingestion.md:115] */
    port out Autopilot_Camera_Serial : Serial_data {
        attribute protocol_family : String = "UART serial";
        doc /* [Source: avenger_v2_5_sysml_v2_ingestion.md:115] */
        flow out Autopilot_Camera_Serial_flow : Serial_data;
    }
    doc /* [Source: avenger_v2_5_sysml_v2_ingestion.md:120] */
    port out Autopilot_GNSS_Serial : Serial_data {
        attribute protocol_family : String = "UART serial";
        doc /* [Source: avenger_v2_5_sysml_v2_ingestion.md:120] */
        flow out Autopilot_GNSS_Serial_flow : Serial_data;
    }
    doc /* [Source: avenger_v2_5_sysml_v2_ingestion.md:121] */
    port out GNSS_RF_Feed : GNSS_signal {
        attribute protocol_family : String = "Coaxial RF";
        doc /* [Source: avenger_v2_5_sysml_v2_ingestion.md:121] */
        flow out GNSS_RF_Feed_flow : GNSS_signal;
    }
    doc /* [Source: avenger_v2_5_sysml_v2_ingestion.md:119] */
    port inout Autopilot_RPI_Serial : Serial_data {
        attribute protocol_family : String = "UART serial";
    }
    doc /* [Source: avenger_v2_5_sysml_v2_ingestion.md:123] */
    port out Autopilot_Radio_Serial : Serial_data {
        attribute protocol_family : String = "UART serial";
        doc /* [Source: avenger_v2_5_sysml_v2_ingestion.md:123] */
        flow out Autopilot_Radio_Serial_flow : Serial_data;
    }
    doc /* [Source: avenger_v2_5_sysml_v2_ingestion.md:125] */
    port out Radio_RF_Feed_Upper : RF_signal {
        attribute protocol_family : String = "Coaxial RF";
        doc /* [Source: avenger_v2_5_sysml_v2_ingestion.md:125] */
        flow out Radio_RF_Feed_Upper_flow : RF_signal;
    }
    doc /* [Source: avenger_v2_5_sysml_v2_ingestion.md:126] */
    port out Radio_RF_Feed_Lower : RF_signal {
        attribute protocol_family : String = "Coaxial RF";
        doc /* [Source: avenger_v2_5_sysml_v2_ingestion.md:126] */
        flow out Radio_RF_Feed_Lower_flow : RF_signal;
    }
    doc /* [Source: avenger_v2_5_sysml_v2_ingestion.md:117] */
    port out External_USB : USB_data {
        attribute protocol_family : String = "USB";
        doc /* [Source: avenger_v2_5_sysml_v2_ingestion.md:117] */
        flow out External_USB_flow : USB_data;
    }
    doc /* [Source: avenger_v2_5_sysml_v2_ingestion.md:130, esad-icd-excalibur-ab00-0054.md:306, esad-icd-excalibur-ab00-0054.md:307 [prototype-reference] [Derived]] */
    port out RPI_ESAD_RS_485 : Binary_message_frame {
        attribute protocol_family : String = "RS-485 half duplex";
        doc /* [Source: avenger_v2_5_sysml_v2_ingestion.md:130, esad-icd-excalibur-ab00-0054.md:306, esad-icd-excalibur-ab00-0054.md:307 [prototype-reference] [Derived]] */
        flow out RPI_ESAD_RS_485_flow : Binary_message_frame;
    }
    doc /* [Source: avenger_v2_5_sysml_v2_ingestion.md:131] */
    port out RPI_ESAD_Analog_Trigger : Analog_trigger_level {
        attribute protocol_family : String = "Discrete GPIO";
        doc /* [Source: avenger_v2_5_sysml_v2_ingestion.md:131] */
        flow out RPI_ESAD_Analog_Trigger_flow : Analog_trigger_level;
    }
    doc /* [Source: avenger_v2_5_sysml_v2_ingestion.md:132, esad-icd-excalibur-ab00-0054.md:203 [prototype-reference] [Derived]] */
    port out Proximity_Sensor_Trigger : Trigger_event {
        attribute protocol_family : String = "Discrete active low";
        doc /* [Source: avenger_v2_5_sysml_v2_ingestion.md:132, esad-icd-excalibur-ab00-0054.md:203 [prototype-reference] [Derived]] */
        flow out Proximity_Sensor_Trigger_flow : Trigger_event;
    }
    doc /* [Source: avenger_v2_5_sysml_v2_ingestion.md:133] */
    port out ESAD_Warhead_Initiation : In_line_initiation_sequence {
        attribute protocol_family : String = "Pyrotechnic initiation";
        doc /* [Source: avenger_v2_5_sysml_v2_ingestion.md:133] */
        flow out ESAD_Warhead_Initiation_flow : In_line_initiation_sequence;
    }
    doc /* [Source: esad-icd-excalibur-ab00-0054.md:272 [prototype-reference] [Derived]] */
    port in ESAD_Power_Input_J100 : _14_to_32_V_DC_nominal_28_V {
        attribute protocol_family : String = "DC power";
        doc /* [Source: esad-icd-excalibur-ab00-0054.md:272 [prototype-reference] [Derived]] */
        flow in ESAD_Power_Input_J100_flow : _14_to_32_V_DC_nominal_28_V;
    }
    doc /* [Source: esad-icd-excalibur-ab00-0054.md:285 [prototype-reference] [Derived]] */
    port in ESAD_Arm_Enable_DSC_IN1 : _1_ms_period_50_percent_duty {
        attribute protocol_family : String = "Discrete PWM";
        doc /* [Source: esad-icd-excalibur-ab00-0054.md:285 [prototype-reference] [Derived]] */
        flow in ESAD_Arm_Enable_DSC_IN1_flow : _1_ms_period_50_percent_duty;
    }
    doc /* [Source: esad-icd-excalibur-ab00-0054.md:284 [prototype-reference] [Derived]] */
    port in ESAD_Umbilical_Continuity : Resistance_below_0_5_Ohm_at_20_mA {
        attribute protocol_family : String = "Analog continuity";
        doc /* [Source: esad-icd-excalibur-ab00-0054.md:284 [prototype-reference] [Derived]] */
        flow in ESAD_Umbilical_Continuity_flow : Resistance_below_0_5_Ohm_at_20_mA;
    }
    doc /* [Source: esad-icd-excalibur-ab00-0054.md:201 [prototype-reference] [Derived]] */
    port inout ESAD_Sensor_Board_UART : Sensor_data_frame {
        attribute protocol_family : String = "UART";
    }
    doc /* [Source: esad-icd-excalibur-ab00-0054.md:205 [prototype-reference] [Derived]] */
    port out ESAD_Sensor_Board_Power_5V : _5_V_DC {
        attribute protocol_family : String = "DC power";
        doc /* [Source: esad-icd-excalibur-ab00-0054.md:205 [prototype-reference] [Derived]] */
        flow out ESAD_Sensor_Board_Power_5V_flow : _5_V_DC;
    }
    doc /* [Source: esad-icd-excalibur-ab00-0054.md:203 [prototype-reference] [Derived]] */
    port in ESAD_Sensor_IRQ : Trigger_event {
        attribute protocol_family : String = "Discrete active low";
        doc /* [Source: esad-icd-excalibur-ab00-0054.md:203 [prototype-reference] [Derived]] */
        flow in ESAD_Sensor_IRQ_flow : Trigger_event;
    }
    doc /* [Source: esad-icd-excalibur-ab00-0054.md:213, esad-icd-excalibur-ab00-0054.md:613 [prototype-reference] [Derived]] */
    port out ESAD_Detonator_High_Voltage : Firing_pulse_up_to_1800_V {
        attribute protocol_family : String = "High voltage";
        doc /* [Source: esad-icd-excalibur-ab00-0054.md:213, esad-icd-excalibur-ab00-0054.md:613 [prototype-reference] [Derived]] */
        flow out ESAD_Detonator_High_Voltage_flow : Firing_pulse_up_to_1800_V;
    }
    doc /* [Source: avenger_v2_5_sysml_v2_ingestion.md:134] */
    port in ESAD_Safe_Arm_Interlock : Safe_or_armed_state {
        attribute protocol_family : String = "Discrete interlock";
        doc /* [Source: avenger_v2_5_sysml_v2_ingestion.md:134] */
        flow in ESAD_Safe_Arm_Interlock_flow : Safe_or_armed_state;
    }
    doc /* [Source: avenger_v2_5_sysml_v2_ingestion.md:70] */
    port in UAV_Power_Interlock : Power_ON_or_OFF {
        attribute protocol_family : String = "Discrete interlock";
        doc /* [Source: avenger_v2_5_sysml_v2_ingestion.md:70] */
        flow in UAV_Power_Interlock_flow : Power_ON_or_OFF;
    }
    doc /* [Source: a5-prep-and-safety-rev7.md:321] */
    port in Warhead_RBF_Interlock : Safe_or_armed {
        attribute protocol_family : String = "Discrete interlock";
        doc /* [Source: a5-prep-and-safety-rev7.md:321] */
        flow in Warhead_RBF_Interlock_flow : Safe_or_armed;
    }
    doc /* [Source: a5-prep-and-safety-rev7.md:112] */
    port out Payload_Bay_Cable : Detonator_firing_pulse {
        attribute protocol_family : String = "Discrete firing circuit";
        doc /* [Source: a5-prep-and-safety-rev7.md:112] */
        flow out Payload_Bay_Cable_flow : Detonator_firing_pulse;
    }
    doc /* [Source: uav_launcher_pl_40_sysml_v2_ingestion_manual.md:132] */
    port out Launcher_Pneumatic_Supply : Air_at_14_bar_maximum {
        attribute protocol_family : String = "Pneumatic";
        doc /* [Source: uav_launcher_pl_40_sysml_v2_ingestion_manual.md:132] */
        flow out Launcher_Pneumatic_Supply_flow : Air_at_14_bar_maximum;
    }
    doc /* [Source: uav_launcher_pl_40_sysml_v2_ingestion_manual.md:82] */
    port out Launcher_Trigger_Command : Dual_switch_launch_command {
        attribute protocol_family : String = "Electrical discrete";
        doc /* [Source: uav_launcher_pl_40_sysml_v2_ingestion_manual.md:82] */
        flow out Launcher_Trigger_Command_flow : Dual_switch_launch_command;
    }
    doc /* [Source: uav_launcher_pl_40_sysml_v2_ingestion_manual.md:81] */
    port out Launcher_Trigger_Power : _18_V_DC {
        attribute protocol_family : String = "DC power";
        doc /* [Source: uav_launcher_pl_40_sysml_v2_ingestion_manual.md:81] */
        flow out Launcher_Trigger_Power_flow : _18_V_DC;
    }
    doc /* [Source: a5-user-manual-2.md:1273] */
    port inout GCS_UAV_Telemetry_Link : Telemetry_and_command_frames {
        attribute protocol_family : String = "RF 4.4 to 5.0 GHz";
    }
    doc /* [Source: a5-user-manual-2.md:1687] */
    port inout GCS_Antenna_RF : RF_link {
        attribute protocol_family : String = "RF 4.4 to 5.0 GHz";
    }
    doc /* [Source: a5-user-manual-2.md:1681] */
    port out GCS_Rotator_Control : Azimuth_command {
        attribute protocol_family : String = "Rotator control";
        doc /* [Source: a5-user-manual-2.md:1681] */
        flow out GCS_Rotator_Control_flow : Azimuth_command;
    }
    doc /* [Source: a5-user-manual-2.md:404] */
    port inout GCS_Tablet_Network : Application_data {
        attribute protocol_family : String = "IP Ethernet or Wi-Fi";
    }
    doc /* [Source: a5-user-manual-2.md:1690] */
    port out GCS_Ground_Radio_Power : _2_W_output_setting {
        attribute protocol_family : String = "RF control";
        doc /* [Source: a5-user-manual-2.md:1690] */
        flow out GCS_Ground_Radio_Power_flow : _2_W_output_setting;
    }
    doc /* [unit: m/s] */
    assert constraint assert_PL_01_range {
        PL_01 >= 30 and PL_01 <= 30;
    }
    doc /* [unit: m/s] */
    assert constraint assert_PL_02_range {
        PL_02 <= 38;
    }
    doc /* [unit: m/s] */
    assert constraint assert_PL_03_range {
        PL_03 <= 55;
    }
    doc /* [unit: deg] */
    assert constraint assert_PL_04_range {
        PL_04 <= 22;
    }
    doc /* [unit: m/s] */
    assert constraint assert_PL_05_range {
        PL_05 >= 26;
    }
    doc /* [unit: min] */
    assert constraint assert_PL_06_range {
        PL_06 >= 0 and PL_06 <= 90;
    }
    doc /* [unit: km] */
    assert constraint assert_PL_07_range {
        PL_07 >= 0 and PL_07 <= 60;
    }
    doc /* [unit: km] */
    assert constraint assert_PL_08_range {
        PL_08 >= 60 and PL_08 <= 180;
    }
    doc /* [unit: m] */
    assert constraint assert_PL_09_range {
        PL_09 >= 1.8 and PL_09 <= 1.8;
    }
    doc /* [unit: m] */
    assert constraint assert_PL_10_range {
        PL_10 >= 1.6 and PL_10 <= 1.6;
    }
    doc /* [unit: m] */
    assert constraint assert_PL_11_range {
        PL_11 >= 1.1 and PL_11 <= 1.1;
    }
    doc /* [unit: kg] */
    assert constraint assert_PL_12_range {
        PL_12 <= 17;
    }
    doc /* [unit: kg] */
    assert constraint assert_PL_13_range {
        PL_13 <= 5;
    }
    doc /* [unit: units] */
    assert constraint assert_PL_14_range {
        PL_14 >= 4 and PL_14 <= 4;
    }
    doc /* [unit: units] */
    assert constraint assert_PL_15_range {
        PL_15 >= 4 and PL_15 <= 4;
    }
    doc /* [unit: units] */
    assert constraint assert_PL_16_range {
        PL_16 >= 4 and PL_16 <= 4;
    }
    doc /* [unit: units] */
    assert constraint assert_PL_17_range {
        PL_17 >= 4 and PL_17 <= 4;
    }
    doc /* [unit: units] */
    assert constraint assert_PL_18_range {
        PL_18 >= 8 and PL_18 <= 8;
    }
    doc /* [unit: cm] */
    assert constraint assert_PL_19_range {
        PL_19 >= 970 and PL_19 <= 970;
    }
    doc /* [unit: cm] */
    assert constraint assert_PL_20_range {
        PL_20 >= 150 and PL_20 <= 150;
    }
    doc /* [unit: cm] */
    assert constraint assert_PL_21_range {
        PL_21 >= 120 and PL_21 <= 120;
    }
    doc /* [unit: V] */
    assert constraint assert_PL_22_range {
        PL_22 >= 8 and PL_22 <= 8;
    }
    doc /* [unit: V] */
    assert constraint assert_PL_23_range {
        PL_23 >= 36 and PL_23 <= 36;
    }
    doc /* [unit: V] */
    assert constraint assert_PL_24_range {
        PL_24 >= 50.4 and PL_24 <= 50.4;
    }
    doc /* [unit: deg] */
    assert constraint assert_PL_25_range {
        PL_25 >= -45 and PL_25 <= 135;
    }
    doc /* [unit: deg] */
    assert constraint assert_PL_26_range {
        PL_26 >= -165 and PL_26 <= 165;
    }
    doc /* [unit: X] */
    assert constraint assert_PL_27_range {
        PL_27 >= 1 and PL_27 <= 40;
    }
    doc /* [unit: pixels] */
    assert constraint assert_PL_28_range {
        PL_28 >= 1280 and PL_28 <= 1280;
    }
    doc /* [unit: pixels] */
    assert constraint assert_PL_29_range {
        PL_29 >= 720 and PL_29 <= 720;
    }
    doc /* [unit: pixels] */
    assert constraint assert_PL_30_range {
        PL_30 >= 1280 and PL_30 <= 1280;
    }
    doc /* [unit: pixels] */
    assert constraint assert_PL_31_range {
        PL_31 >= 720 and PL_31 <= 720;
    }
    doc /* [unit: V] */
    assert constraint assert_PL_32_range {
        PL_32 >= 49 and PL_32 <= 49;
    }
    doc /* [unit: V] */
    assert constraint assert_PL_33_range {
        PL_33 >= 50 and PL_33 <= 50;
    }
    doc /* [unit: m/s] */
    assert constraint assert_PL_34_range {
        PL_34 >= 0 and PL_34 <= 3;
    }
    doc /* [unit: m/s] */
    assert constraint assert_PL_35_range {
        PL_35 >= 10;
    }
    doc /* [unit: m] */
    assert constraint assert_PL_36_range {
        PL_36 >= 50;
    }
    doc /* [unit: m] */
    assert constraint assert_PL_37_range {
        PL_37 >= 300 and PL_37 <= 300;
    }
    doc /* [unit: chars] */
    assert constraint assert_PL_38_range {
        PL_38 >= 0 and PL_38 <= 24;
    }
    doc /* [unit: W] */
    assert constraint assert_PL_39_range {
        PL_39 >= 2 and PL_39 <= 2;
    }
    doc /* [unit: bar] */
    assert constraint assert_PL_40_range {
        PL_40 >= 13 and PL_40 <= 13;
    }
    doc /* [unit: bar] */
    assert constraint assert_PL_41_range {
        PL_41 >= 14 and PL_41 <= 14;
    }
    doc /* [unit: s] */
    assert constraint assert_PL_42_range {
        PL_42 >= 2 and PL_42 <= 2;
    }
    doc /* [unit: s] */
    assert constraint assert_PL_43_range {
        PL_43 >= 5 and PL_43 <= 5;
    }
    doc /* [unit: deg] */
    assert constraint assert_PL_44_range {
        PL_44 <= 15;
    }
    doc /* [unit: m/s] */
    assert constraint assert_PL_45_range {
        PL_45 <= 55;
    }
    doc /* [unit: V] */
    assert constraint assert_PL_46_range {
        PL_46 >= 14 and PL_46 <= 14;
    }
    doc /* [unit: V] */
    assert constraint assert_PL_47_range {
        PL_47 >= 32 and PL_47 <= 32;
    }
    doc /* [unit: V] */
    assert constraint assert_PL_48_range {
        PL_48 >= 28 and PL_48 <= 28;
    }
    doc /* [unit: Ohm] */
    assert constraint assert_PL_49_range {
        PL_49 >= 0 and PL_49 <= 0.5;
    }
    doc /* [unit: mA] */
    assert constraint assert_PL_50_range {
        PL_50 >= 20 and PL_50 <= 20;
    }
    doc /* [unit: VDC] */
    assert constraint assert_PL_51_range {
        PL_51 >= 0 and PL_51 <= 0.7;
    }
    doc /* [unit: VDC] */
    assert constraint assert_PL_52_range {
        PL_52 >= 2.5 and PL_52 <= 2.5;
    }
    doc /* [unit: VDC] */
    assert constraint assert_PL_53_range {
        PL_53 >= 3.3 and PL_53 <= 3.3;
    }
    doc /* [unit: ms] */
    assert constraint assert_PL_54_range {
        PL_54 >= 1 and PL_54 <= 1;
    }
    doc /* [unit: percent] */
    assert constraint assert_PL_55_range {
        PL_55 >= 50 and PL_55 <= 50;
    }
    doc /* [unit: bps] */
    assert constraint assert_PL_56_range {
        PL_56 >= 115200 and PL_56 <= 115200;
    }
    doc /* [unit: Hz] */
    assert constraint assert_PL_57_range {
        PL_57 >= 100 and PL_57 <= 100;
    }
    doc /* [unit: ms] */
    assert constraint assert_PL_58_range {
        PL_58 >= 0 and PL_58 <= 5;
    }
    doc /* [unit: ms] */
    assert constraint assert_PL_59_range {
        PL_59 >= 0 and PL_59 <= 10;
    }
    doc /* [unit: V] */
    assert constraint assert_PL_60_range {
        PL_60 >= 0 and PL_60 <= 1800;
    }
    doc /* [unit: bytes] */
    assert constraint assert_PL_61_range {
        PL_61 >= 5 and PL_61 <= 5;
    }
    doc /* [unit: bytes] */
    assert constraint assert_PL_62_range {
        PL_62 >= 14 and PL_62 <= 14;
    }
    doc /* [unit: g] */
    assert constraint assert_PL_63_range {
        PL_63 >= 0.0039 and PL_63 <= 0.0039;
    }
    doc /* [unit: kg] */
    assert constraint assert_PL_64_range {
        PL_64 <= 30;
    }
    doc /* [unit: m/s] */
    assert constraint assert_PL_65_range {
        PL_65 <= 25;
    }
    doc /* [unit: deg] */
    assert constraint assert_PL_66_range {
        PL_66 >= 12 and PL_66 <= 12;
    }
    doc /* [unit: bar] */
    assert constraint assert_PL_67_range {
        PL_67 <= 14;
    }
    doc /* [unit: bar] */
    assert constraint assert_PL_68_range {
        PL_68 <= 16;
    }
    doc /* [unit: kg] */
    assert constraint assert_PL_69_range {
        PL_69 >= 68 and PL_69 <= 68;
    }
    doc /* [unit: kg] */
    assert constraint assert_PL_70_range {
        PL_70 >= 43 and PL_70 <= 43;
    }
    doc /* [unit: kg] */
    assert constraint assert_PL_71_range {
        PL_71 >= 25 and PL_71 <= 25;
    }
    doc /* [unit: min] */
    assert constraint assert_PL_72_range {
        PL_72 >= 0 and PL_72 <= 5;
    }
    doc /* [unit: degC] */
    assert constraint assert_PL_73_range {
        PL_73 >= -20 and PL_73 <= -20;
    }
    doc /* [unit: degC] */
    assert constraint assert_PL_74_range {
        PL_74 >= 50 and PL_74 <= 50;
    }
    doc /* [unit: V] */
    assert constraint assert_PL_75_range {
        PL_75 >= 18 and PL_75 <= 18;
    }
    doc /* [unit: mAh] */
    assert constraint assert_PL_76_range {
        PL_76 >= 6000 and PL_76 <= 6000;
    }
    doc /* [unit: V] */
    assert constraint assert_PL_77_range {
        PL_77 <= 14.5;
    }
    doc /* [unit: V] */
    assert constraint assert_PL_78_range {
        PL_78 >= 16;
    }
    doc /* [unit: s] */
    assert constraint assert_PL_79_range {
        PL_79 >= 5 and PL_79 <= 5;
    }
    doc /* [unit: launches] */
    assert constraint assert_PL_80_range {
        PL_80 <= 100;
    }
    doc /* [unit: mm] */
    assert constraint assert_PL_81_range {
        PL_81 >= 271 and PL_81 <= 271;
    }
    doc /* [unit: mm] */
    assert constraint assert_PL_82_range {
        PL_82 >= 206.5 and PL_82 <= 206.5;
    }
    doc /* [unit: mm] */
    assert constraint assert_PL_83_range {
        PL_83 >= 232.5 and PL_83 <= 232.5;
    }
    doc /* [unit: mm] */
    assert constraint assert_PL_84_range {
        PL_84 >= 0 and PL_84 <= 200;
    }
    doc /* [unit: mm] */
    assert constraint assert_PL_85_range {
        PL_85 >= 0 and PL_85 <= 100;
    }
    doc /* [unit: mm] */
    assert constraint assert_PL_86_range {
        PL_86 >= 1115 and PL_86 <= 1115;
    }
    doc /* [unit: mm] */
    assert constraint assert_PL_87_range {
        PL_87 >= 602 and PL_87 <= 602;
    }
    doc /* [unit: s] */
    assert constraint assert_PL_88_range {
        PL_88 >= 2;
    }
    doc /* [unit: min] */
    assert constraint assert_PL_89_range {
        PL_89 >= 0 and PL_89 <= 55;
    }
    doc /* [unit: min] */
    assert constraint assert_PL_90_range {
        PL_90 >= 0 and PL_90 <= 130;
    }
    doc /* [unit: degC] */
    assert constraint assert_PL_91_range {
        PL_91 >= 10 and PL_91 <= 10;
    }
    doc /* [unit: degC] */
    assert constraint assert_PL_92_range {
        PL_92 >= 40 and PL_92 <= 40;
    }
    doc /* [unit: m] */
    assert constraint assert_PL_93_range {
        PL_93 >= 5 and PL_93 <= 5;
    }
    doc /* [unit: m] */
    assert constraint assert_PL_94_range {
        PL_94 >= 1.28 and PL_94 <= 1.28;
    }
    doc /* Synthesized deterministic package lifecycle state machine. */
    state def Interface_Table_LifecycleState {
        state Interface_Table_System_State;
        state Interface_Table_InitState;
        state Interface_Table_ActiveState;
        transition Initial_to_Interface_Table_System_State first Initial then Interface_Table_System_State;
        transition Interface_Table_System_State_to_Interface_Table_InitState_on_Initialize_Interface_Table first Interface_Table_System_State accept Initialize_Interface_Table then Interface_Table_InitState;
        transition Interface_Table_InitState_to_Interface_Table_ActiveState_on_Verify_Interface_Table first Interface_Table_InitState accept Verify_Interface_Table then Interface_Table_ActiveState;
        transition Interface_Table_ActiveState_to_Terminal first Interface_Table_ActiveState then Terminal;
    }
    doc /* Synthesized deterministic package lifecycle state machine. */
    state def OEM_Bill_of_Materials_LifecycleState {
        state Air_Vehicle_Avenger_V2_5_State;
        state Airframe_Fuselage_State;
        state Airframe_Payload_Bay_State;
        transition Initial_to_Air_Vehicle_Avenger_V2_5_State first Initial then Air_Vehicle_Avenger_V2_5_State;
        transition Air_Vehicle_Avenger_V2_5_State_to_Airframe_Fuselage_State_on_Initialize_OEM_Bill_of_Materials first Air_Vehicle_Avenger_V2_5_State accept Initialize_OEM_Bill_of_Materials then Airframe_Fuselage_State;
        transition Airframe_Fuselage_State_to_Airframe_Payload_Bay_State_on_Verify_OEM_Bill_of_Materials first Airframe_Fuselage_State accept Verify_OEM_Bill_of_Materials then Airframe_Payload_Bay_State;
        transition Airframe_Payload_Bay_State_to_Terminal first Airframe_Payload_Bay_State then Terminal;
    }
    doc /* Synthesized deterministic package lifecycle state machine. */
    state def Parametric_Limits_Table_LifecycleState {
        state Parametric_Limits_Table_System_State;
        state Parametric_Limits_Table_InitState;
        state Parametric_Limits_Table_ActiveState;
        transition Initial_to_Parametric_Limits_Table_System_State first Initial then Parametric_Limits_Table_System_State;
        transition Parametric_Limits_Table_System_State_to_Parametric_Limits_Table_InitState_on_Initialize_Parametric_Limits_Table first Parametric_Limits_Table_System_State accept Initialize_Parametric_Limits_Table then Parametric_Limits_Table_InitState;
        transition Parametric_Limits_Table_InitState_to_Parametric_Limits_Table_ActiveState_on_Verify_Parametric_Limits_Table first Parametric_Limits_Table_InitState accept Verify_Parametric_Limits_Table then Parametric_Limits_Table_ActiveState;
        transition Parametric_Limits_Table_ActiveState_to_Terminal first Parametric_Limits_Table_ActiveState then Terminal;
    }
    doc /* [Source: avenger_v2_5_sysml_v2_ingestion.md:7] */
    part def Air_Vehicle_Avenger_V2_5 {
        doc /* [Source: avenger_v2_5_sysml_v2_ingestion.md:7] */
        attribute component_name : String = "Top-level air vehicle boundary enclosing all onboard subsystems";
        doc /* [Source: avenger_v2_5_sysml_v2_ingestion.md:7] */
        attribute interface_item : String = "Onboard subsystem boundaries; external RBF keys; external interface board";
        doc /* [unit: kg] [Source: avenger_v2_5_sysml_v2_ingestion.md:7] */
        attribute mass : String = "Not stated";
        doc /* [Source: avenger_v2_5_sysml_v2_ingestion.md:7] */
        attribute part_number : String = "Not stated";
        doc /* [unit: W] [Source: avenger_v2_5_sysml_v2_ingestion.md:7] */
        attribute power : String = "Not stated";
    }
    doc /* [Source: a5-user-manual-2.md:336] */
    part def Airframe_Fuselage {
        doc /* [Source: a5-user-manual-2.md:336] */
        attribute component_name : String = "Fuselage assembly with hatches closed and vertical stabilizer attached; battery included";
        doc /* [Source: a5-user-manual-2.md:336] */
        attribute interface_item : String = "Payload bay; wing mounting brackets; ruddervator mounting shafts; RBF sockets";
        doc /* [unit: kg] [Source: a5-user-manual-2.md:336] */
        attribute mass : String = "Not stated";
        doc /* [Source: a5-user-manual-2.md:336] */
        attribute part_number : String = "Not stated";
        doc /* [unit: W] [Source: a5-user-manual-2.md:336] */
        attribute power : String = "Not stated";
    }
    doc /* [Source: a5-prep-and-safety-rev7.md:102, a5-prep-and-safety-rev7.md:138] */
    part def Airframe_Payload_Bay {
        doc /* [Source: a5-prep-and-safety-rev7.md:102, a5-prep-and-safety-rev7.md:138] */
        attribute component_name : String = "Payload bay with hatch, mounting brackets and retaining rings";
        doc /* [Source: a5-prep-and-safety-rev7.md:102, a5-prep-and-safety-rev7.md:138] */
        attribute interface_item : String = "Warhead mounting brackets; ESAD payload cables; hatch lock";
        doc /* [unit: kg] [Source: a5-prep-and-safety-rev7.md:102, a5-prep-and-safety-rev7.md:138] */
        attribute mass : String = "Not stated";
        doc /* [Source: a5-prep-and-safety-rev7.md:102, a5-prep-and-safety-rev7.md:138] */
        attribute part_number : String = "Not stated";
        doc /* [unit: W] [Source: a5-prep-and-safety-rev7.md:102, a5-prep-and-safety-rev7.md:138] */
        attribute power : String = "Not stated";
    }
    doc /* [Source: avenger_v2_5_sysml_v2_ingestion.md:17] */
    part def Automotive_Fuse_200A {
        doc /* [Source: avenger_v2_5_sysml_v2_ingestion.md:17] */
        attribute component_name : String = "200 A automotive main power fuse";
        doc /* [Source: avenger_v2_5_sysml_v2_ingestion.md:17] */
        attribute interface_item : String = "Battery to power meter main power line";
        doc /* [unit: kg] [Source: avenger_v2_5_sysml_v2_ingestion.md:17] */
        attribute mass : String = "Not stated";
        doc /* [Source: avenger_v2_5_sysml_v2_ingestion.md:17] */
        attribute part_number : String = "Not stated";
        doc /* [unit: W] [Source: avenger_v2_5_sysml_v2_ingestion.md:17] */
        attribute power : String = "Not stated";
    }
    doc /* [Source: avenger_v2_5_sysml_v2_ingestion.md:10, avenger_v2_5_sysml_v2_ingestion.md:144] */
    part def Autopilot_Computing_Board_Cube_Orange_Plus {
        doc /* [Source: avenger_v2_5_sysml_v2_ingestion.md:10, avenger_v2_5_sysml_v2_ingestion.md:144] */
        attribute component_name : String = "Autopilot computing board and sensor fusion controller";
        doc /* [Source: avenger_v2_5_sysml_v2_ingestion.md:10, avenger_v2_5_sysml_v2_ingestion.md:144] */
        attribute interface_item : String = "CAN 1; CAN 2; serial links; USB; ETH";
        doc /* [unit: kg] [Source: avenger_v2_5_sysml_v2_ingestion.md:10, avenger_v2_5_sysml_v2_ingestion.md:144] */
        attribute mass : String = "Not stated";
        doc /* [Source: avenger_v2_5_sysml_v2_ingestion.md:10, avenger_v2_5_sysml_v2_ingestion.md:144] */
        attribute part_number : String = "Cube Orange Plus";
        doc /* [unit: W] [Source: avenger_v2_5_sysml_v2_ingestion.md:10, avenger_v2_5_sysml_v2_ingestion.md:144] */
        attribute power : String = "Not stated";
    }
    doc /* [Source: avenger_v2_5_sysml_v2_ingestion.md:8] */
    part def Autopilot_Stack_Module_ASTK_A5_V2_5 {
        doc /* [Source: avenger_v2_5_sysml_v2_ingestion.md:8] */
        attribute component_name : String = "Autopilot stack module boundary";
        doc /* [Source: avenger_v2_5_sysml_v2_ingestion.md:8] */
        attribute interface_item : String = "EPS module; autopilot computing board; ETH switch; RPI; GNSS module";
        doc /* [unit: kg] [Source: avenger_v2_5_sysml_v2_ingestion.md:8] */
        attribute mass : String = "Not stated";
        doc /* [Source: avenger_v2_5_sysml_v2_ingestion.md:8] */
        attribute part_number : String = "ASTK A5 V2.5";
        doc /* [unit: W] [Source: avenger_v2_5_sysml_v2_ingestion.md:8] */
        attribute power : String = "Not stated";
    }
    doc /* [Source: avenger_v2_5_sysml_v2_ingestion.md:16] */
    part def Battery_12S2P_Li_Metal_BEI {
        doc /* [Source: avenger_v2_5_sysml_v2_ingestion.md:16] */
        attribute component_name : String = "Removable 12S2P Li metal battery with maximus20 cells";
        doc /* [Source: avenger_v2_5_sysml_v2_ingestion.md:16] */
        attribute interface_item : String = "36 to 50.4 V DC main power; retaining strap; locking connector";
        doc /* [unit: kg] [Source: avenger_v2_5_sysml_v2_ingestion.md:16] */
        attribute mass : String = "Not stated";
        doc /* [Source: avenger_v2_5_sysml_v2_ingestion.md:16] */
        attribute part_number : String = "Not stated";
        doc /* [unit: W] [Source: avenger_v2_5_sysml_v2_ingestion.md:16] */
        attribute power : String = "Not stated";
    }
    doc /* [Source: avenger_v2_5_sysml_v2_ingestion.md:50] */
    part def CAN_1_Autopilot_EPS_Junction_Node {
        doc /* [Source: avenger_v2_5_sysml_v2_ingestion.md:50] */
        attribute component_name : String = "CAN 1 junction linking autopilot, EPS and CAN 1 trunk";
        doc /* [Source: avenger_v2_5_sysml_v2_ingestion.md:50] */
        attribute interface_item : String = "CAN 1 trunk; EPS tap; autopilot tap";
        doc /* [unit: kg] [Source: avenger_v2_5_sysml_v2_ingestion.md:50] */
        attribute mass : String = "Not stated";
        doc /* [Source: avenger_v2_5_sysml_v2_ingestion.md:50] */
        attribute part_number : String = "Not stated";
        doc /* [unit: W] [Source: avenger_v2_5_sysml_v2_ingestion.md:50] */
        attribute power : String = "Not stated";
    }
    doc /* [Source: avenger_v2_5_sysml_v2_ingestion.md:51] */
    part def CAN_1_Power_Meter_Junction_Node {
        doc /* [Source: avenger_v2_5_sysml_v2_ingestion.md:51] */
        attribute component_name : String = "CAN 1 junction below the power meter";
        doc /* [Source: avenger_v2_5_sysml_v2_ingestion.md:51] */
        attribute interface_item : String = "CAN 1 970 cm trunk; power meter; CAN 1 150 cm branch";
        doc /* [unit: kg] [Source: avenger_v2_5_sysml_v2_ingestion.md:51] */
        attribute mass : String = "Not stated";
        doc /* [Source: avenger_v2_5_sysml_v2_ingestion.md:51] */
        attribute part_number : String = "Not stated";
        doc /* [unit: W] [Source: avenger_v2_5_sysml_v2_ingestion.md:51] */
        attribute power : String = "Not stated";
    }
    doc /* [Source: avenger_v2_5_sysml_v2_ingestion.md:52] */
    part def CAN_1_Ruddervator_Splitter_Junction_Node {
        doc /* [Source: avenger_v2_5_sysml_v2_ingestion.md:52] */
        attribute component_name : String = "CAN 1 hub splitting the 150 cm branch into four 120 cm servo stubs";
        doc /* [Source: avenger_v2_5_sysml_v2_ingestion.md:52] */
        attribute interface_item : String = "Four CAN 1 120 cm branches to Ruddervator Servos #1 to #4";
        doc /* [unit: kg] [Source: avenger_v2_5_sysml_v2_ingestion.md:52] */
        attribute mass : String = "Not stated";
        doc /* [Source: avenger_v2_5_sysml_v2_ingestion.md:52] */
        attribute part_number : String = "Not stated";
        doc /* [unit: W] [Source: avenger_v2_5_sysml_v2_ingestion.md:52] */
        attribute power : String = "Not stated";
    }
    doc /* [Source: avenger_v2_5_sysml_v2_ingestion.md:53] */
    part def CAN_2_Servo_5_Series_Junction_Node {
        doc /* [Source: avenger_v2_5_sysml_v2_ingestion.md:53] */
        attribute component_name : String = "CAN 2 series junction at Wing Servo #5";
        doc /* [Source: avenger_v2_5_sysml_v2_ingestion.md:53] */
        attribute interface_item : String = "Splitter PCB; Wing Servo #5; next series segment";
        doc /* [unit: kg] [Source: avenger_v2_5_sysml_v2_ingestion.md:53] */
        attribute mass : String = "Not stated";
        doc /* [Source: avenger_v2_5_sysml_v2_ingestion.md:53] */
        attribute part_number : String = "Not stated";
        doc /* [unit: W] [Source: avenger_v2_5_sysml_v2_ingestion.md:53] */
        attribute power : String = "Not stated";
    }
    doc /* [Source: avenger_v2_5_sysml_v2_ingestion.md:54] */
    part def CAN_2_Servo_6_Series_Junction_Node {
        doc /* [Source: avenger_v2_5_sysml_v2_ingestion.md:54] */
        attribute component_name : String = "CAN 2 series junction at Wing Servo #6";
        doc /* [Source: avenger_v2_5_sysml_v2_ingestion.md:54] */
        attribute interface_item : String = "Splitter PCB; Wing Servo #6; next series segment";
        doc /* [unit: kg] [Source: avenger_v2_5_sysml_v2_ingestion.md:54] */
        attribute mass : String = "Not stated";
        doc /* [Source: avenger_v2_5_sysml_v2_ingestion.md:54] */
        attribute part_number : String = "Not stated";
        doc /* [unit: W] [Source: avenger_v2_5_sysml_v2_ingestion.md:54] */
        attribute power : String = "Not stated";
    }
    doc /* [Source: avenger_v2_5_sysml_v2_ingestion.md:55] */
    part def CAN_2_Servo_7_Series_Junction_Node {
        doc /* [Source: avenger_v2_5_sysml_v2_ingestion.md:55] */
        attribute component_name : String = "CAN 2 series junction at Wing Servo #7";
        doc /* [Source: avenger_v2_5_sysml_v2_ingestion.md:55] */
        attribute interface_item : String = "Splitter PCB; Wing Servo #7; next series segment";
        doc /* [unit: kg] [Source: avenger_v2_5_sysml_v2_ingestion.md:55] */
        attribute mass : String = "Not stated";
        doc /* [Source: avenger_v2_5_sysml_v2_ingestion.md:55] */
        attribute part_number : String = "Not stated";
        doc /* [unit: W] [Source: avenger_v2_5_sysml_v2_ingestion.md:55] */
        attribute power : String = "Not stated";
    }
    doc /* [Source: avenger_v2_5_sysml_v2_ingestion.md:26, avenger_v2_5_sysml_v2_ingestion.md:157] */
    part def CAN_power_splitter_PCB {
        doc /* [Source: avenger_v2_5_sysml_v2_ingestion.md:26, avenger_v2_5_sysml_v2_ingestion.md:157] */
        attribute component_name : String = "Servo power splitter and CAN 2 series pass-through board";
        doc /* [Source: avenger_v2_5_sysml_v2_ingestion.md:26, avenger_v2_5_sysml_v2_ingestion.md:157] */
        attribute interface_item : String = "Four 8 V inputs from EPS; CAN 2 input from autopilot; series CAN 2 daisy chain to Servos #5 to #8";
        doc /* [unit: kg] [Source: avenger_v2_5_sysml_v2_ingestion.md:26, avenger_v2_5_sysml_v2_ingestion.md:157] */
        attribute mass : String = "Not stated";
        doc /* [Source: avenger_v2_5_sysml_v2_ingestion.md:26, avenger_v2_5_sysml_v2_ingestion.md:157] */
        attribute part_number : String = "Not stated";
        doc /* [unit: W] [Source: avenger_v2_5_sysml_v2_ingestion.md:26, avenger_v2_5_sysml_v2_ingestion.md:157] */
        attribute power : String = "Not stated";
    }
    doc /* [Source: avenger_v2_5_sysml_v2_ingestion.md:36] */
    part def Camera_Compute_Module_Trip6 {
        doc /* [Source: avenger_v2_5_sysml_v2_ingestion.md:36] */
        attribute component_name : String = "Gimbal control, video and target tracking computer";
        doc /* [Source: avenger_v2_5_sysml_v2_ingestion.md:36] */
        attribute interface_item : String = "ETH; serial from autopilot; power and HDMI to gimbal";
        doc /* [unit: kg] [Source: avenger_v2_5_sysml_v2_ingestion.md:36] */
        attribute mass : String = "Not stated";
        doc /* [Source: avenger_v2_5_sysml_v2_ingestion.md:36] */
        attribute part_number : String = "Trip6";
        doc /* [unit: W] [Source: avenger_v2_5_sysml_v2_ingestion.md:36] */
        attribute power : String = "Not stated";
    }
    doc /* [Source: avenger_v2_5_sysml_v2_ingestion.md:9, avenger_v2_5_sysml_v2_ingestion.md:145] */
    part def EPS_Module {
        doc /* [Source: avenger_v2_5_sysml_v2_ingestion.md:9, avenger_v2_5_sysml_v2_ingestion.md:145] */
        attribute component_name : String = "Electronic power system module with DC/DC converters, load switches and MCU";
        doc /* [Source: avenger_v2_5_sysml_v2_ingestion.md:9, avenger_v2_5_sysml_v2_ingestion.md:145] */
        attribute interface_item : String = "8 V servo rails; 12 V radio; 14 V ESAD; 50 V igniters; pitot and magnetometer power";
        doc /* [unit: kg] [Source: avenger_v2_5_sysml_v2_ingestion.md:9, avenger_v2_5_sysml_v2_ingestion.md:145] */
        attribute mass : String = "Not stated";
        doc /* [Source: avenger_v2_5_sysml_v2_ingestion.md:9, avenger_v2_5_sysml_v2_ingestion.md:145] */
        attribute part_number : String = "Not stated";
        doc /* [unit: W] [Source: avenger_v2_5_sysml_v2_ingestion.md:9, avenger_v2_5_sysml_v2_ingestion.md:145] */
        attribute power : String = "Not stated";
    }
    doc /* [Source: avenger_v2_5_sysml_v2_ingestion.md:79, avenger_v2_5_sysml_v2_ingestion.md:86, avenger_v2_5_sysml_v2_ingestion.md:155] */
    part def EPS_Servo_Power_8V_Rail {
        doc /* [Source: avenger_v2_5_sysml_v2_ingestion.md:79, avenger_v2_5_sysml_v2_ingestion.md:86, avenger_v2_5_sysml_v2_ingestion.md:155] */
        attribute component_name : String = "Regulated 8 V servo power distribution with four ruddervator branches and four splitter inputs";
        doc /* [Source: avenger_v2_5_sysml_v2_ingestion.md:79, avenger_v2_5_sysml_v2_ingestion.md:86, avenger_v2_5_sysml_v2_ingestion.md:155] */
        attribute interface_item : String = "8 V DC to Servos #1 to #8 through direct branches and the CAN/power splitter PCB";
        doc /* [unit: kg] [Source: avenger_v2_5_sysml_v2_ingestion.md:79, avenger_v2_5_sysml_v2_ingestion.md:86, avenger_v2_5_sysml_v2_ingestion.md:155] */
        attribute mass : String = "Not stated";
        doc /* [Source: avenger_v2_5_sysml_v2_ingestion.md:79, avenger_v2_5_sysml_v2_ingestion.md:86, avenger_v2_5_sysml_v2_ingestion.md:155] */
        attribute part_number : String = "Not stated";
        doc /* [unit: W] [Source: avenger_v2_5_sysml_v2_ingestion.md:79, avenger_v2_5_sysml_v2_ingestion.md:86, avenger_v2_5_sysml_v2_ingestion.md:155] */
        attribute power : String = "Not stated";
    }
    doc /* [Source: avenger_v2_5_sysml_v2_ingestion.md:45, a5-user-manual-2.md:1984, esad-icd-excalibur-ab00-0054.md:105 [prototype-reference] [Derived]] */
    part def ESAD {
        doc /* [Source: avenger_v2_5_sysml_v2_ingestion.md:45, a5-user-manual-2.md:1984, esad-icd-excalibur-ab00-0054.md:105 [prototype-reference] [Derived]] */
        attribute component_name : String = "Electronic Safe and Arm Device, Critical / DAL-A, all-electronic safety and arming device";
        doc /* [Source: avenger_v2_5_sysml_v2_ingestion.md:45, a5-user-manual-2.md:1984, esad-icd-excalibur-ab00-0054.md:105 [prototype-reference] [Derived]] */
        attribute interface_item : String = "J100 system; J102 sensor board; J401 detonator; RS-485; DSC_IN1 arm enable; UMB continuity";
        doc /* [unit: kg] [Source: avenger_v2_5_sysml_v2_ingestion.md:45, a5-user-manual-2.md:1984, esad-icd-excalibur-ab00-0054.md:105 [prototype-reference] [Derived]] */
        attribute mass : String = "Not stated";
        doc /* [Source: avenger_v2_5_sysml_v2_ingestion.md:45, a5-user-manual-2.md:1984, esad-icd-excalibur-ab00-0054.md:105 [prototype-reference] [Derived]] */
        attribute part_number : String = "Artron generic ESAD board-level prototype";
        doc /* [unit: W] [Source: avenger_v2_5_sysml_v2_ingestion.md:45, a5-user-manual-2.md:1984, esad-icd-excalibur-ab00-0054.md:105 [prototype-reference] [Derived]] */
        attribute power : String = "Not stated";
    }
    doc /* [Source: esad-icd-excalibur-ab00-0054.md:108 [prototype-reference] [Derived]] */
    part def ESAD_Detonator {
        doc /* [Source: esad-icd-excalibur-ab00-0054.md:108 [prototype-reference] [Derived]] */
        attribute component_name : String = "LEEFI or EFI detonator";
        doc /* [Source: esad-icd-excalibur-ab00-0054.md:108 [prototype-reference] [Derived]] */
        attribute interface_item : String = "ESAD J401 HV_OUT and HV_GND";
        doc /* [unit: kg] [Source: esad-icd-excalibur-ab00-0054.md:108 [prototype-reference] [Derived]] */
        attribute mass : String = "Not stated";
        doc /* [Source: esad-icd-excalibur-ab00-0054.md:108 [prototype-reference] [Derived]] */
        attribute part_number : String = "Not stated";
        doc /* [unit: W] [Source: esad-icd-excalibur-ab00-0054.md:108 [prototype-reference] [Derived]] */
        attribute power : String = "Not stated";
    }
    doc /* [Source: esad-icd-excalibur-ab00-0054.md:167, esad-icd-excalibur-ab00-0054.md:193, esad-icd-excalibur-ab00-0054.md:233 [prototype-reference] [Derived]] */
    part def ESAD_Harness {
        doc /* [Source: esad-icd-excalibur-ab00-0054.md:167, esad-icd-excalibur-ab00-0054.md:193, esad-icd-excalibur-ab00-0054.md:233 [prototype-reference] [Derived]] */
        attribute component_name : String = "ESAD board and sensor board mating connectors and crimps";
        doc /* [Source: esad-icd-excalibur-ab00-0054.md:167, esad-icd-excalibur-ab00-0054.md:193, esad-icd-excalibur-ab00-0054.md:233 [prototype-reference] [Derived]] */
        attribute interface_item : String = "J100; J102; sensor board J1";
        doc /* [unit: kg] [Source: esad-icd-excalibur-ab00-0054.md:167, esad-icd-excalibur-ab00-0054.md:193, esad-icd-excalibur-ab00-0054.md:233 [prototype-reference] [Derived]] */
        attribute mass : String = "Not stated";
        doc /* [Source: esad-icd-excalibur-ab00-0054.md:167, esad-icd-excalibur-ab00-0054.md:193, esad-icd-excalibur-ab00-0054.md:233 [prototype-reference] [Derived]] */
        attribute part_number : String = "Harwin G125-2241696F1; Harwin G125-2241096F1; Harwin G125-0020005; Molex 501330-0800";
        doc /* [unit: W] [Source: esad-icd-excalibur-ab00-0054.md:167, esad-icd-excalibur-ab00-0054.md:193, esad-icd-excalibur-ab00-0054.md:233 [prototype-reference] [Derived]] */
        attribute power : String = "Not stated";
    }
    doc /* [Source: avenger_v2_5_sysml_v2_ingestion.md:49] */
    part def ESAD_RBF_Key {
        doc /* [Source: avenger_v2_5_sysml_v2_ingestion.md:49] */
        attribute component_name : String = "ESAD arming sequence Remove Before Flight key";
        doc /* [Source: avenger_v2_5_sysml_v2_ingestion.md:49] */
        attribute interface_item : String = "ESAD discrete interlock";
        doc /* [unit: kg] [Source: avenger_v2_5_sysml_v2_ingestion.md:49] */
        attribute mass : String = "Not stated";
        doc /* [Source: avenger_v2_5_sysml_v2_ingestion.md:49] */
        attribute part_number : String = "Not stated";
        doc /* [unit: W] [Source: avenger_v2_5_sysml_v2_ingestion.md:49] */
        attribute power : String = "Not stated";
    }
    doc /* [Source: esad-icd-excalibur-ab00-0054.md:159 [prototype-reference] [Derived]] */
    part def ESAD_Sensor_Board {
        doc /* [Source: esad-icd-excalibur-ab00-0054.md:159 [prototype-reference] [Derived]] */
        attribute component_name : String = "Proximity and impact sensor board with UART, IRQ_L and 5 V interface";
        doc /* [Source: esad-icd-excalibur-ab00-0054.md:159 [prototype-reference] [Derived]] */
        attribute interface_item : String = "J1 cable to ESAD J102; 5 V power; UART; IRQ_L trigger";
        doc /* [unit: kg] [Source: esad-icd-excalibur-ab00-0054.md:159 [prototype-reference] [Derived]] */
        attribute mass : String = "Not stated";
        doc /* [Source: esad-icd-excalibur-ab00-0054.md:159 [prototype-reference] [Derived]] */
        attribute part_number : String = "Not stated";
        doc /* [unit: W] [Source: esad-icd-excalibur-ab00-0054.md:159 [prototype-reference] [Derived]] */
        attribute power : String = "Not stated";
    }
    doc /* [Source: esad-icd-excalibur-ab00-0054.md:112 [prototype-reference] [Derived]] */
    part def ESAD_Umbilical {
        doc /* [Source: esad-icd-excalibur-ab00-0054.md:112 [prototype-reference] [Derived]] */
        attribute component_name : String = "Umbilical continuity connection";
        doc /* [Source: esad-icd-excalibur-ab00-0054.md:112 [prototype-reference] [Derived]] */
        attribute interface_item : String = "ESAD J100 UMB and UMB_RTN continuity line";
        doc /* [unit: kg] [Source: esad-icd-excalibur-ab00-0054.md:112 [prototype-reference] [Derived]] */
        attribute mass : String = "Not stated";
        doc /* [Source: esad-icd-excalibur-ab00-0054.md:112 [prototype-reference] [Derived]] */
        attribute part_number : String = "Not stated";
        doc /* [unit: W] [Source: esad-icd-excalibur-ab00-0054.md:112 [prototype-reference] [Derived]] */
        attribute power : String = "Not stated";
    }
    doc /* [Source: avenger_v2_5_sysml_v2_ingestion.md:19] */
    part def ESC_IBEX160 {
        doc /* [Source: avenger_v2_5_sysml_v2_ingestion.md:19] */
        attribute component_name : String = "Electronic speed controller";
        doc /* [Source: avenger_v2_5_sysml_v2_ingestion.md:19] */
        attribute interface_item : String = "Three-phase motor drive; PWM throttle; UART telemetry";
        doc /* [unit: kg] [Source: avenger_v2_5_sysml_v2_ingestion.md:19] */
        attribute mass : String = "Not stated";
        doc /* [Source: avenger_v2_5_sysml_v2_ingestion.md:19] */
        attribute part_number : String = "IBEX160";
        doc /* [unit: W] [Source: avenger_v2_5_sysml_v2_ingestion.md:19] */
        attribute power : String = "Not stated";
    }
    doc /* [Source: a5-prep-and-safety-rev7.md:94] */
    part def ESD_Grounding_Point {
        doc /* [Source: a5-prep-and-safety-rev7.md:94] */
        attribute component_name : String = "ESD grounding point marked by a yellow label";
        doc /* [Source: a5-prep-and-safety-rev7.md:94] */
        attribute interface_item : String = "Operator electrostatic discharge equalization point";
        doc /* [unit: kg] [Source: a5-prep-and-safety-rev7.md:94] */
        attribute mass : String = "Not stated";
        doc /* [Source: a5-prep-and-safety-rev7.md:94] */
        attribute part_number : String = "Not stated";
        doc /* [unit: W] [Source: a5-prep-and-safety-rev7.md:94] */
        attribute power : String = "Not stated";
    }
    doc /* [Source: avenger_v2_5_sysml_v2_ingestion.md:11] */
    part def ETH_Switch {
        doc /* [Source: avenger_v2_5_sysml_v2_ingestion.md:11] */
        attribute component_name : String = "IP network switch for onboard systems";
        doc /* [Source: avenger_v2_5_sysml_v2_ingestion.md:11] */
        attribute interface_item : String = "ETH to RPI, camera compute module, radio module and external interface board";
        doc /* [unit: kg] [Source: avenger_v2_5_sysml_v2_ingestion.md:11] */
        attribute mass : String = "Not stated";
        doc /* [Source: avenger_v2_5_sysml_v2_ingestion.md:11] */
        attribute part_number : String = "Not stated";
        doc /* [unit: W] [Source: avenger_v2_5_sysml_v2_ingestion.md:11] */
        attribute power : String = "Not stated";
    }
    doc /* [Source: avenger_v2_5_sysml_v2_ingestion.md:47] */
    part def External_Interface_Board_USB_ETH {
        doc /* [Source: avenger_v2_5_sysml_v2_ingestion.md:47] */
        attribute component_name : String = "External USB and ETH interface board";
        doc /* [Source: avenger_v2_5_sysml_v2_ingestion.md:47] */
        attribute interface_item : String = "USB from autopilot; ETH from ETH switch";
        doc /* [unit: kg] [Source: avenger_v2_5_sysml_v2_ingestion.md:47] */
        attribute mass : String = "Not stated";
        doc /* [Source: avenger_v2_5_sysml_v2_ingestion.md:47] */
        attribute part_number : String = "Not stated";
        doc /* [unit: W] [Source: avenger_v2_5_sysml_v2_ingestion.md:47] */
        attribute power : String = "Not stated";
    }
    doc /* [Source: a5-user-manual-2.md:350] */
    part def GCS_Battery {
        doc /* [Source: a5-user-manual-2.md:350] */
        attribute component_name : String = "Ground control station battery, quantity 2";
        doc /* [Source: a5-user-manual-2.md:350] */
        attribute interface_item : String = "GCS DC power";
        doc /* [unit: kg] [Source: a5-user-manual-2.md:350] */
        attribute mass : String = "Not stated";
        doc /* [Source: a5-user-manual-2.md:350] */
        attribute part_number : String = "Not stated";
        doc /* [unit: W] [Source: a5-user-manual-2.md:350] */
        attribute power : String = "Not stated";
    }
    doc /* [Source: a5-user-manual-2.md:354, a5-user-manual-2.md:355, a5-user-manual-2.md:356, a5-user-manual-2.md:357] */
    part def GCS_Cabling {
        doc /* [Source: a5-user-manual-2.md:354, a5-user-manual-2.md:355, a5-user-manual-2.md:356, a5-user-manual-2.md:357] */
        attribute component_name : String = "Power, Ethernet, antenna and LAN cables with ODU and N-type connectors";
        doc /* [Source: a5-user-manual-2.md:354, a5-user-manual-2.md:355, a5-user-manual-2.md:356, a5-user-manual-2.md:357] */
        attribute interface_item : String = "ODU connector; N-type connector; Ethernet";
        doc /* [unit: kg] [Source: a5-user-manual-2.md:354, a5-user-manual-2.md:355, a5-user-manual-2.md:356, a5-user-manual-2.md:357] */
        attribute mass : String = "Not stated";
        doc /* [Source: a5-user-manual-2.md:354, a5-user-manual-2.md:355, a5-user-manual-2.md:356, a5-user-manual-2.md:357] */
        attribute part_number : String = "Not stated";
        doc /* [unit: W] [Source: a5-user-manual-2.md:354, a5-user-manual-2.md:355, a5-user-manual-2.md:356, a5-user-manual-2.md:357] */
        attribute power : String = "Not stated";
    }
    doc /* [Source: a5-user-manual-2.md:347] */
    part def GCS_Ground_Box {
        doc /* [Source: a5-user-manual-2.md:347] */
        attribute component_name : String = "Ground control station network and power box";
        doc /* [Source: a5-user-manual-2.md:347] */
        attribute interface_item : String = "Radio and antenna connections; DC power";
        doc /* [unit: kg] [Source: a5-user-manual-2.md:347] */
        attribute mass : String = "Not stated";
        doc /* [Source: a5-user-manual-2.md:347] */
        attribute part_number : String = "Not stated";
        doc /* [unit: W] [Source: a5-user-manual-2.md:347] */
        attribute power : String = "Not stated";
    }
    doc /* [Source: a5-user-manual-2.md:353] */
    part def GCS_MARS_Antenna {
        doc /* [Source: a5-user-manual-2.md:353] */
        attribute component_name : String = "MARS 23 dBi antenna";
        doc /* [Source: a5-user-manual-2.md:353] */
        attribute interface_item : String = "N-type connector; RF link";
        doc /* [unit: kg] [Source: a5-user-manual-2.md:353] */
        attribute mass : String = "Not stated";
        doc /* [Source: a5-user-manual-2.md:353] */
        attribute part_number : String = "MARS 23dBi";
        doc /* [unit: W] [Source: a5-user-manual-2.md:353] */
        attribute power : String = "Not stated";
    }
    doc /* [Source: a5-user-manual-2.md:346] */
    part def GCS_Radio_Box {
        doc /* [Source: a5-user-manual-2.md:346] */
        attribute component_name : String = "Ground control station radio box";
        doc /* [Source: a5-user-manual-2.md:346] */
        attribute interface_item : String = "RF link; Ethernet; DC power";
        doc /* [unit: kg] [Source: a5-user-manual-2.md:346] */
        attribute mass : String = "Not stated";
        doc /* [Source: a5-user-manual-2.md:346] */
        attribute part_number : String = "Not stated";
        doc /* [unit: W] [Source: a5-user-manual-2.md:346] */
        attribute power : String = "Not stated";
    }
    doc /* [Source: a5-user-manual-2.md:348] */
    part def GCS_Rotator {
        doc /* [Source: a5-user-manual-2.md:348] */
        attribute component_name : String = "Antenna rotator";
        doc /* [Source: a5-user-manual-2.md:348] */
        attribute interface_item : String = "Antenna mount; rotator control; direction feedback";
        doc /* [unit: kg] [Source: a5-user-manual-2.md:348] */
        attribute mass : String = "Not stated";
        doc /* [Source: a5-user-manual-2.md:348] */
        attribute part_number : String = "Not stated";
        doc /* [unit: W] [Source: a5-user-manual-2.md:348] */
        attribute power : String = "Not stated";
    }
    doc /* [Source: a5-user-manual-2.md:351] */
    part def GCS_Tablet_FZ_G2 {
        doc /* [Source: a5-user-manual-2.md:351] */
        attribute component_name : String = "Panasonic FZ-G2 tablet, quantity 2";
        doc /* [Source: a5-user-manual-2.md:351] */
        attribute interface_item : String = "Wi-Fi or Ethernet to ground station; Swarm C2 application";
        doc /* [unit: kg] [Source: a5-user-manual-2.md:351] */
        attribute mass : String = "Not stated";
        doc /* [Source: a5-user-manual-2.md:351] */
        attribute part_number : String = "Panasonic FZ-G2";
        doc /* [unit: W] [Source: a5-user-manual-2.md:351] */
        attribute power : String = "Not stated";
    }
    doc /* [Source: a5-user-manual-2.md:349] */
    part def GCS_Tripod {
        doc /* [Source: a5-user-manual-2.md:349] */
        attribute component_name : String = "Gitzo tripod with head";
        doc /* [Source: a5-user-manual-2.md:349] */
        attribute interface_item : String = "Antenna and rotator mount";
        doc /* [unit: kg] [Source: a5-user-manual-2.md:349] */
        attribute mass : String = "Not stated";
        doc /* [Source: a5-user-manual-2.md:349] */
        attribute part_number : String = "Gitzo";
        doc /* [unit: W] [Source: a5-user-manual-2.md:349] */
        attribute power : String = "Not stated";
    }
    doc /* [Source: avenger_v2_5_sysml_v2_ingestion.md:14] */
    part def GNSS_Antenna_Talysman_TW3972EXF {
        doc /* [Source: avenger_v2_5_sysml_v2_ingestion.md:14] */
        attribute component_name : String = "GNSS receive antenna";
        doc /* [Source: avenger_v2_5_sysml_v2_ingestion.md:14] */
        attribute interface_item : String = "Coaxial RF feed from GNSS module";
        doc /* [unit: kg] [Source: avenger_v2_5_sysml_v2_ingestion.md:14] */
        attribute mass : String = "Not stated";
        doc /* [Source: avenger_v2_5_sysml_v2_ingestion.md:14] */
        attribute part_number : String = "Talysman TW3972EXF";
        doc /* [unit: W] [Source: avenger_v2_5_sysml_v2_ingestion.md:14] */
        attribute power : String = "Not stated";
    }
    doc /* [Source: avenger_v2_5_sysml_v2_ingestion.md:13] */
    part def GNSS_Module_Septentrio_Asterx_m3_pro {
        doc /* [Source: avenger_v2_5_sysml_v2_ingestion.md:13] */
        attribute component_name : String = "Absolute position and velocity receiver";
        doc /* [Source: avenger_v2_5_sysml_v2_ingestion.md:13] */
        attribute interface_item : String = "Serial from autopilot; RF to GNSS antenna";
        doc /* [unit: kg] [Source: avenger_v2_5_sysml_v2_ingestion.md:13] */
        attribute mass : String = "Not stated";
        doc /* [Source: avenger_v2_5_sysml_v2_ingestion.md:13] */
        attribute part_number : String = "Septentrio Asterx-m3 pro";
        doc /* [unit: W] [Source: avenger_v2_5_sysml_v2_ingestion.md:13] */
        attribute power : String = "Not stated";
    }
    doc /* [Source: avenger_v2_5_sysml_v2_ingestion.md:35] */
    part def Gimbal_Nighthawk2UZ {
        doc /* [Source: avenger_v2_5_sysml_v2_ingestion.md:35] */
        attribute component_name : String = "IR and RGB camera gimbal payload";
        doc /* [Source: avenger_v2_5_sysml_v2_ingestion.md:35] */
        attribute interface_item : String = "Power and HDMI data from camera compute module";
        doc /* [unit: kg] [Source: avenger_v2_5_sysml_v2_ingestion.md:35] */
        attribute mass : String = "Not stated";
        doc /* [Source: avenger_v2_5_sysml_v2_ingestion.md:35] */
        attribute part_number : String = "Nighthawk2UZ";
        doc /* [unit: W] [Source: avenger_v2_5_sysml_v2_ingestion.md:35] */
        attribute power : String = "Not stated";
    }
    doc /* Synthesized system component for Interface_Table */
    part def Interface_Table_System {
        doc /* [Source: avenger_v2_5_sysml_v2_ingestion.md:72, avenger_v2_5_sysml_v2_ingestion.md:171] */
        port inout CAN_1_Trunk_970_cm : CAN_frame {
            attribute protocol_family : String = "CAN bus DroneCAN";
        }
        doc /* [Source: avenger_v2_5_sysml_v2_ingestion.md:73] */
        port inout CAN_1_EPS_Tap : CAN_frame {
            attribute protocol_family : String = "CAN bus DroneCAN";
        }
        doc /* [Source: avenger_v2_5_sysml_v2_ingestion.md:74, avenger_v2_5_sysml_v2_ingestion.md:172] */
        port inout CAN_1_Branch_150_cm : CAN_frame {
            attribute protocol_family : String = "CAN bus DroneCAN";
        }
        doc /* [Source: avenger_v2_5_sysml_v2_ingestion.md:75, avenger_v2_5_sysml_v2_ingestion.md:173] */
        port inout CAN_1_Ruddervator_Servo_1_Branch_120_cm : Servo_command_and_status_frame {
            attribute protocol_family : String = "CAN bus DroneCAN";
        }
        doc /* [Source: avenger_v2_5_sysml_v2_ingestion.md:76, avenger_v2_5_sysml_v2_ingestion.md:173] */
        port inout CAN_1_Ruddervator_Servo_2_Branch_120_cm : Servo_command_and_status_frame {
            attribute protocol_family : String = "CAN bus DroneCAN";
        }
        doc /* [Source: avenger_v2_5_sysml_v2_ingestion.md:77, avenger_v2_5_sysml_v2_ingestion.md:173] */
        port inout CAN_1_Ruddervator_Servo_3_Branch_120_cm : Servo_command_and_status_frame {
            attribute protocol_family : String = "CAN bus DroneCAN";
        }
        doc /* [Source: avenger_v2_5_sysml_v2_ingestion.md:78, avenger_v2_5_sysml_v2_ingestion.md:173] */
        port inout CAN_1_Ruddervator_Servo_4_Branch_120_cm : Servo_command_and_status_frame {
            attribute protocol_family : String = "CAN bus DroneCAN";
        }
        doc /* [Source: avenger_v2_5_sysml_v2_ingestion.md:79, avenger_v2_5_sysml_v2_ingestion.md:155] */
        port out Servo_Power_8V_Ruddervator_Servo_1 : _8_V_DC {
            attribute protocol_family : String = "DC power";
            doc /* [Source: avenger_v2_5_sysml_v2_ingestion.md:79, avenger_v2_5_sysml_v2_ingestion.md:155] */
            flow out Servo_Power_8V_Ruddervator_Servo_1_flow : _8_V_DC;
        }
        doc /* [Source: avenger_v2_5_sysml_v2_ingestion.md:80, avenger_v2_5_sysml_v2_ingestion.md:155] */
        port out Servo_Power_8V_Ruddervator_Servo_2 : _8_V_DC {
            attribute protocol_family : String = "DC power";
            doc /* [Source: avenger_v2_5_sysml_v2_ingestion.md:80, avenger_v2_5_sysml_v2_ingestion.md:155] */
            flow out Servo_Power_8V_Ruddervator_Servo_2_flow : _8_V_DC;
        }
        doc /* [Source: avenger_v2_5_sysml_v2_ingestion.md:81, avenger_v2_5_sysml_v2_ingestion.md:155] */
        port out Servo_Power_8V_Ruddervator_Servo_3 : _8_V_DC {
            attribute protocol_family : String = "DC power";
            doc /* [Source: avenger_v2_5_sysml_v2_ingestion.md:81, avenger_v2_5_sysml_v2_ingestion.md:155] */
            flow out Servo_Power_8V_Ruddervator_Servo_3_flow : _8_V_DC;
        }
        doc /* [Source: avenger_v2_5_sysml_v2_ingestion.md:82, avenger_v2_5_sysml_v2_ingestion.md:155] */
        port out Servo_Power_8V_Ruddervator_Servo_4 : _8_V_DC {
            attribute protocol_family : String = "DC power";
            doc /* [Source: avenger_v2_5_sysml_v2_ingestion.md:82, avenger_v2_5_sysml_v2_ingestion.md:155] */
            flow out Servo_Power_8V_Ruddervator_Servo_4_flow : _8_V_DC;
        }
        doc /* [Source: avenger_v2_5_sysml_v2_ingestion.md:83, avenger_v2_5_sysml_v2_ingestion.md:157] */
        port out Servo_Power_8V_Splitter_Input_1 : _8_V_DC {
            attribute protocol_family : String = "DC power";
            doc /* [Source: avenger_v2_5_sysml_v2_ingestion.md:83, avenger_v2_5_sysml_v2_ingestion.md:157] */
            flow out Servo_Power_8V_Splitter_Input_1_flow : _8_V_DC;
        }
        doc /* [Source: avenger_v2_5_sysml_v2_ingestion.md:84, avenger_v2_5_sysml_v2_ingestion.md:157] */
        port out Servo_Power_8V_Splitter_Input_2 : _8_V_DC {
            attribute protocol_family : String = "DC power";
            doc /* [Source: avenger_v2_5_sysml_v2_ingestion.md:84, avenger_v2_5_sysml_v2_ingestion.md:157] */
            flow out Servo_Power_8V_Splitter_Input_2_flow : _8_V_DC;
        }
        doc /* [Source: avenger_v2_5_sysml_v2_ingestion.md:85, avenger_v2_5_sysml_v2_ingestion.md:157] */
        port out Servo_Power_8V_Splitter_Input_3 : _8_V_DC {
            attribute protocol_family : String = "DC power";
            doc /* [Source: avenger_v2_5_sysml_v2_ingestion.md:85, avenger_v2_5_sysml_v2_ingestion.md:157] */
            flow out Servo_Power_8V_Splitter_Input_3_flow : _8_V_DC;
        }
        doc /* [Source: avenger_v2_5_sysml_v2_ingestion.md:86, avenger_v2_5_sysml_v2_ingestion.md:157] */
        port out Servo_Power_8V_Splitter_Input_4 : _8_V_DC {
            attribute protocol_family : String = "DC power";
            doc /* [Source: avenger_v2_5_sysml_v2_ingestion.md:86, avenger_v2_5_sysml_v2_ingestion.md:157] */
            flow out Servo_Power_8V_Splitter_Input_4_flow : _8_V_DC;
        }
        doc /* [Source: avenger_v2_5_sysml_v2_ingestion.md:87, avenger_v2_5_sysml_v2_ingestion.md:156] */
        port out Servo_Power_8V_Wing_Servo_5 : _8_V_DC {
            attribute protocol_family : String = "DC power";
            doc /* [Source: avenger_v2_5_sysml_v2_ingestion.md:87, avenger_v2_5_sysml_v2_ingestion.md:156] */
            flow out Servo_Power_8V_Wing_Servo_5_flow : _8_V_DC;
        }
        doc /* [Source: avenger_v2_5_sysml_v2_ingestion.md:88, avenger_v2_5_sysml_v2_ingestion.md:156] */
        port out Servo_Power_8V_Wing_Servo_6 : _8_V_DC {
            attribute protocol_family : String = "DC power";
            doc /* [Source: avenger_v2_5_sysml_v2_ingestion.md:88, avenger_v2_5_sysml_v2_ingestion.md:156] */
            flow out Servo_Power_8V_Wing_Servo_6_flow : _8_V_DC;
        }
        doc /* [Source: avenger_v2_5_sysml_v2_ingestion.md:89, avenger_v2_5_sysml_v2_ingestion.md:156] */
        port out Servo_Power_8V_Wing_Servo_7 : _8_V_DC {
            attribute protocol_family : String = "DC power";
            doc /* [Source: avenger_v2_5_sysml_v2_ingestion.md:89, avenger_v2_5_sysml_v2_ingestion.md:156] */
            flow out Servo_Power_8V_Wing_Servo_7_flow : _8_V_DC;
        }
        doc /* [Source: avenger_v2_5_sysml_v2_ingestion.md:90, avenger_v2_5_sysml_v2_ingestion.md:156] */
        port out Servo_Power_8V_Wing_Servo_8 : _8_V_DC {
            attribute protocol_family : String = "DC power";
            doc /* [Source: avenger_v2_5_sysml_v2_ingestion.md:90, avenger_v2_5_sysml_v2_ingestion.md:156] */
            flow out Servo_Power_8V_Wing_Servo_8_flow : _8_V_DC;
        }
        doc /* [Source: avenger_v2_5_sysml_v2_ingestion.md:91, avenger_v2_5_sysml_v2_ingestion.md:157] */
        port out CAN_2_Splitter_Input : CAN_frame {
            attribute protocol_family : String = "CAN bus DroneCAN";
            doc /* [Source: avenger_v2_5_sysml_v2_ingestion.md:91, avenger_v2_5_sysml_v2_ingestion.md:157] */
            flow out CAN_2_Splitter_Input_flow : CAN_frame;
        }
        doc /* [Source: avenger_v2_5_sysml_v2_ingestion.md:92, avenger_v2_5_sysml_v2_ingestion.md:99] */
        port inout CAN_2_Daisy_Chain_Segment_5_to_6 : Servo_command_and_status_frame {
            attribute protocol_family : String = "CAN bus DroneCAN";
        }
        doc /* [Source: avenger_v2_5_sysml_v2_ingestion.md:99, avenger_v2_5_sysml_v2_ingestion.md:103] */
        port inout CAN_2_Daisy_Chain_Segment_6_to_7 : Servo_command_and_status_frame {
            attribute protocol_family : String = "CAN bus DroneCAN";
        }
        doc /* [Source: avenger_v2_5_sysml_v2_ingestion.md:103, avenger_v2_5_sysml_v2_ingestion.md:105] */
        port inout CAN_2_Daisy_Chain_Segment_7_to_8 : Servo_command_and_status_frame {
            attribute protocol_family : String = "CAN bus DroneCAN";
        }
        doc /* [Source: avenger_v2_5_sysml_v2_ingestion.md:106, avenger_v2_5_sysml_v2_ingestion.md:108] */
        port inout CAN_2_Magnetometer_Continuation : Sensor_frame {
            attribute protocol_family : String = "CAN bus DroneCAN";
        }
        doc /* [Source: avenger_v2_5_sysml_v2_ingestion.md:114, avenger_v2_5_sysml_v2_ingestion.md:122] */
        port inout ETH_Backbone : IP_packet {
            attribute protocol_family : String = "Ethernet";
        }
        doc /* [Source: avenger_v2_5_sysml_v2_ingestion.md:114] */
        port inout Camera_Module_ETH : IP_packet {
            attribute protocol_family : String = "Ethernet";
        }
        doc /* [Source: avenger_v2_5_sysml_v2_ingestion.md:118] */
        port inout RPI_ETH : IP_packet {
            attribute protocol_family : String = "Ethernet";
        }
        doc /* [Source: avenger_v2_5_sysml_v2_ingestion.md:116] */
        port inout External_ETH : IP_packet {
            attribute protocol_family : String = "Ethernet";
        }
        doc /* [Source: avenger_v2_5_sysml_v2_ingestion.md:115] */
        port out Autopilot_Camera_Serial : Serial_data {
            attribute protocol_family : String = "UART serial";
            doc /* [Source: avenger_v2_5_sysml_v2_ingestion.md:115] */
            flow out Autopilot_Camera_Serial_flow : Serial_data;
        }
        doc /* [Source: avenger_v2_5_sysml_v2_ingestion.md:120] */
        port out Autopilot_GNSS_Serial : Serial_data {
            attribute protocol_family : String = "UART serial";
            doc /* [Source: avenger_v2_5_sysml_v2_ingestion.md:120] */
            flow out Autopilot_GNSS_Serial_flow : Serial_data;
        }
        doc /* [Source: avenger_v2_5_sysml_v2_ingestion.md:121] */
        port out GNSS_RF_Feed : GNSS_signal {
            attribute protocol_family : String = "Coaxial RF";
            doc /* [Source: avenger_v2_5_sysml_v2_ingestion.md:121] */
            flow out GNSS_RF_Feed_flow : GNSS_signal;
        }
        doc /* [Source: avenger_v2_5_sysml_v2_ingestion.md:119] */
        port inout Autopilot_RPI_Serial : Serial_data {
            attribute protocol_family : String = "UART serial";
        }
        doc /* [Source: avenger_v2_5_sysml_v2_ingestion.md:123] */
        port out Autopilot_Radio_Serial : Serial_data {
            attribute protocol_family : String = "UART serial";
            doc /* [Source: avenger_v2_5_sysml_v2_ingestion.md:123] */
            flow out Autopilot_Radio_Serial_flow : Serial_data;
        }
        doc /* [Source: avenger_v2_5_sysml_v2_ingestion.md:125] */
        port out Radio_RF_Feed_Upper : RF_signal {
            attribute protocol_family : String = "Coaxial RF";
            doc /* [Source: avenger_v2_5_sysml_v2_ingestion.md:125] */
            flow out Radio_RF_Feed_Upper_flow : RF_signal;
        }
        doc /* [Source: avenger_v2_5_sysml_v2_ingestion.md:126] */
        port out Radio_RF_Feed_Lower : RF_signal {
            attribute protocol_family : String = "Coaxial RF";
            doc /* [Source: avenger_v2_5_sysml_v2_ingestion.md:126] */
            flow out Radio_RF_Feed_Lower_flow : RF_signal;
        }
        doc /* [Source: avenger_v2_5_sysml_v2_ingestion.md:117] */
        port out External_USB : USB_data {
            attribute protocol_family : String = "USB";
            doc /* [Source: avenger_v2_5_sysml_v2_ingestion.md:117] */
            flow out External_USB_flow : USB_data;
        }
        doc /* [Source: avenger_v2_5_sysml_v2_ingestion.md:130, esad-icd-excalibur-ab00-0054.md:306, esad-icd-excalibur-ab00-0054.md:307 [prototype-reference] [Derived]] */
        port out RPI_ESAD_RS_485 : Binary_message_frame {
            attribute protocol_family : String = "RS-485 half duplex";
            doc /* [Source: avenger_v2_5_sysml_v2_ingestion.md:130, esad-icd-excalibur-ab00-0054.md:306, esad-icd-excalibur-ab00-0054.md:307 [prototype-reference] [Derived]] */
            flow out RPI_ESAD_RS_485_flow : Binary_message_frame;
        }
        doc /* [Source: avenger_v2_5_sysml_v2_ingestion.md:131] */
        port out RPI_ESAD_Analog_Trigger : Analog_trigger_level {
            attribute protocol_family : String = "Discrete GPIO";
            doc /* [Source: avenger_v2_5_sysml_v2_ingestion.md:131] */
            flow out RPI_ESAD_Analog_Trigger_flow : Analog_trigger_level;
        }
        doc /* [Source: avenger_v2_5_sysml_v2_ingestion.md:132, esad-icd-excalibur-ab00-0054.md:203 [prototype-reference] [Derived]] */
        port out Proximity_Sensor_Trigger : Trigger_event {
            attribute protocol_family : String = "Discrete active low";
            doc /* [Source: avenger_v2_5_sysml_v2_ingestion.md:132, esad-icd-excalibur-ab00-0054.md:203 [prototype-reference] [Derived]] */
            flow out Proximity_Sensor_Trigger_flow : Trigger_event;
        }
        doc /* [Source: avenger_v2_5_sysml_v2_ingestion.md:133] */
        port out ESAD_Warhead_Initiation : In_line_initiation_sequence {
            attribute protocol_family : String = "Pyrotechnic initiation";
            doc /* [Source: avenger_v2_5_sysml_v2_ingestion.md:133] */
            flow out ESAD_Warhead_Initiation_flow : In_line_initiation_sequence;
        }
        doc /* [Source: esad-icd-excalibur-ab00-0054.md:272 [prototype-reference] [Derived]] */
        port in ESAD_Power_Input_J100 : _14_to_32_V_DC_nominal_28_V {
            attribute protocol_family : String = "DC power";
            doc /* [Source: esad-icd-excalibur-ab00-0054.md:272 [prototype-reference] [Derived]] */
            flow in ESAD_Power_Input_J100_flow : _14_to_32_V_DC_nominal_28_V;
        }
        doc /* [Source: esad-icd-excalibur-ab00-0054.md:285 [prototype-reference] [Derived]] */
        port in ESAD_Arm_Enable_DSC_IN1 : _1_ms_period_50_percent_duty {
            attribute protocol_family : String = "Discrete PWM";
            doc /* [Source: esad-icd-excalibur-ab00-0054.md:285 [prototype-reference] [Derived]] */
            flow in ESAD_Arm_Enable_DSC_IN1_flow : _1_ms_period_50_percent_duty;
        }
        doc /* [Source: esad-icd-excalibur-ab00-0054.md:284 [prototype-reference] [Derived]] */
        port in ESAD_Umbilical_Continuity : Resistance_below_0_5_Ohm_at_20_mA {
            attribute protocol_family : String = "Analog continuity";
            doc /* [Source: esad-icd-excalibur-ab00-0054.md:284 [prototype-reference] [Derived]] */
            flow in ESAD_Umbilical_Continuity_flow : Resistance_below_0_5_Ohm_at_20_mA;
        }
        doc /* [Source: esad-icd-excalibur-ab00-0054.md:201 [prototype-reference] [Derived]] */
        port inout ESAD_Sensor_Board_UART : Sensor_data_frame {
            attribute protocol_family : String = "UART";
        }
        doc /* [Source: esad-icd-excalibur-ab00-0054.md:205 [prototype-reference] [Derived]] */
        port out ESAD_Sensor_Board_Power_5V : _5_V_DC {
            attribute protocol_family : String = "DC power";
            doc /* [Source: esad-icd-excalibur-ab00-0054.md:205 [prototype-reference] [Derived]] */
            flow out ESAD_Sensor_Board_Power_5V_flow : _5_V_DC;
        }
        doc /* [Source: esad-icd-excalibur-ab00-0054.md:203 [prototype-reference] [Derived]] */
        port in ESAD_Sensor_IRQ : Trigger_event {
            attribute protocol_family : String = "Discrete active low";
            doc /* [Source: esad-icd-excalibur-ab00-0054.md:203 [prototype-reference] [Derived]] */
            flow in ESAD_Sensor_IRQ_flow : Trigger_event;
        }
        doc /* [Source: esad-icd-excalibur-ab00-0054.md:213, esad-icd-excalibur-ab00-0054.md:613 [prototype-reference] [Derived]] */
        port out ESAD_Detonator_High_Voltage : Firing_pulse_up_to_1800_V {
            attribute protocol_family : String = "High voltage";
            doc /* [Source: esad-icd-excalibur-ab00-0054.md:213, esad-icd-excalibur-ab00-0054.md:613 [prototype-reference] [Derived]] */
            flow out ESAD_Detonator_High_Voltage_flow : Firing_pulse_up_to_1800_V;
        }
        doc /* [Source: avenger_v2_5_sysml_v2_ingestion.md:134] */
        port in ESAD_Safe_Arm_Interlock : Safe_or_armed_state {
            attribute protocol_family : String = "Discrete interlock";
            doc /* [Source: avenger_v2_5_sysml_v2_ingestion.md:134] */
            flow in ESAD_Safe_Arm_Interlock_flow : Safe_or_armed_state;
        }
        doc /* [Source: avenger_v2_5_sysml_v2_ingestion.md:70] */
        port in UAV_Power_Interlock : Power_ON_or_OFF {
            attribute protocol_family : String = "Discrete interlock";
            doc /* [Source: avenger_v2_5_sysml_v2_ingestion.md:70] */
            flow in UAV_Power_Interlock_flow : Power_ON_or_OFF;
        }
        doc /* [Source: a5-prep-and-safety-rev7.md:321] */
        port in Warhead_RBF_Interlock : Safe_or_armed {
            attribute protocol_family : String = "Discrete interlock";
            doc /* [Source: a5-prep-and-safety-rev7.md:321] */
            flow in Warhead_RBF_Interlock_flow : Safe_or_armed;
        }
        doc /* [Source: a5-prep-and-safety-rev7.md:112] */
        port out Payload_Bay_Cable : Detonator_firing_pulse {
            attribute protocol_family : String = "Discrete firing circuit";
            doc /* [Source: a5-prep-and-safety-rev7.md:112] */
            flow out Payload_Bay_Cable_flow : Detonator_firing_pulse;
        }
        doc /* [Source: uav_launcher_pl_40_sysml_v2_ingestion_manual.md:132] */
        port out Launcher_Pneumatic_Supply : Air_at_14_bar_maximum {
            attribute protocol_family : String = "Pneumatic";
            doc /* [Source: uav_launcher_pl_40_sysml_v2_ingestion_manual.md:132] */
            flow out Launcher_Pneumatic_Supply_flow : Air_at_14_bar_maximum;
        }
        doc /* [Source: uav_launcher_pl_40_sysml_v2_ingestion_manual.md:82] */
        port out Launcher_Trigger_Command : Dual_switch_launch_command {
            attribute protocol_family : String = "Electrical discrete";
            doc /* [Source: uav_launcher_pl_40_sysml_v2_ingestion_manual.md:82] */
            flow out Launcher_Trigger_Command_flow : Dual_switch_launch_command;
        }
        doc /* [Source: uav_launcher_pl_40_sysml_v2_ingestion_manual.md:81] */
        port out Launcher_Trigger_Power : _18_V_DC {
            attribute protocol_family : String = "DC power";
            doc /* [Source: uav_launcher_pl_40_sysml_v2_ingestion_manual.md:81] */
            flow out Launcher_Trigger_Power_flow : _18_V_DC;
        }
        doc /* [Source: a5-user-manual-2.md:1273] */
        port inout GCS_UAV_Telemetry_Link : Telemetry_and_command_frames {
            attribute protocol_family : String = "RF 4.4 to 5.0 GHz";
        }
        doc /* [Source: a5-user-manual-2.md:1687] */
        port inout GCS_Antenna_RF : RF_link {
            attribute protocol_family : String = "RF 4.4 to 5.0 GHz";
        }
        doc /* [Source: a5-user-manual-2.md:1681] */
        port out GCS_Rotator_Control : Azimuth_command {
            attribute protocol_family : String = "Rotator control";
            doc /* [Source: a5-user-manual-2.md:1681] */
            flow out GCS_Rotator_Control_flow : Azimuth_command;
        }
        doc /* [Source: a5-user-manual-2.md:404] */
        port inout GCS_Tablet_Network : Application_data {
            attribute protocol_family : String = "IP Ethernet or Wi-Fi";
        }
        doc /* [Source: a5-user-manual-2.md:1690] */
        port out GCS_Ground_Radio_Power : _2_W_output_setting {
            attribute protocol_family : String = "RF control";
            doc /* [Source: a5-user-manual-2.md:1690] */
            flow out GCS_Ground_Radio_Power_flow : _2_W_output_setting;
        }
    }
    doc /* [Source: avenger_v2_5_sysml_v2_ingestion.md:44] */
    part def Lethal_Package {
        doc /* [Source: avenger_v2_5_sysml_v2_ingestion.md:44] */
        attribute component_name : String = "Lethal package boundary enclosing ESAD and warhead";
        doc /* [Source: avenger_v2_5_sysml_v2_ingestion.md:44] */
        attribute interface_item : String = "ESAD interfaces; warhead initiation train";
        doc /* [unit: kg] [Source: avenger_v2_5_sysml_v2_ingestion.md:44] */
        attribute mass : String = "Not stated";
        doc /* [Source: avenger_v2_5_sysml_v2_ingestion.md:44] */
        attribute part_number : String = "Not stated";
        doc /* [unit: W] [Source: avenger_v2_5_sysml_v2_ingestion.md:44] */
        attribute power : String = "Not stated";
    }
    doc /* [Source: avenger_v2_5_sysml_v2_ingestion.md:34] */
    part def Magnetometer_mRo_RM3100_Lower {
        doc /* [Source: avenger_v2_5_sysml_v2_ingestion.md:34] */
        attribute component_name : String = "Lower heading and barometric sensor unit";
        doc /* [Source: avenger_v2_5_sysml_v2_ingestion.md:34] */
        attribute interface_item : String = "CAN 2 continuation; Mag Power from EPS";
        doc /* [unit: kg] [Source: avenger_v2_5_sysml_v2_ingestion.md:34] */
        attribute mass : String = "Not stated";
        doc /* [Source: avenger_v2_5_sysml_v2_ingestion.md:34] */
        attribute part_number : String = "mRo RM3100";
        doc /* [unit: W] [Source: avenger_v2_5_sysml_v2_ingestion.md:34] */
        attribute power : String = "Not stated";
    }
    doc /* [Source: avenger_v2_5_sysml_v2_ingestion.md:33] */
    part def Magnetometer_mRo_RM3100_Upper {
        doc /* [Source: avenger_v2_5_sysml_v2_ingestion.md:33] */
        attribute component_name : String = "Upper heading and barometric sensor unit";
        doc /* [Source: avenger_v2_5_sysml_v2_ingestion.md:33] */
        attribute interface_item : String = "CAN 2 continuation; Mag Power from EPS";
        doc /* [unit: kg] [Source: avenger_v2_5_sysml_v2_ingestion.md:33] */
        attribute mass : String = "Not stated";
        doc /* [Source: avenger_v2_5_sysml_v2_ingestion.md:33] */
        attribute part_number : String = "mRo RM3100";
        doc /* [unit: W] [Source: avenger_v2_5_sysml_v2_ingestion.md:33] */
        attribute power : String = "Not stated";
    }
    doc /* [Source: avenger_v2_5_sysml_v2_ingestion.md:20] */
    part def Motor_AXI_5345_16_HD_GOLD_LINE_V3 {
        doc /* [Source: avenger_v2_5_sysml_v2_ingestion.md:20] */
        attribute component_name : String = "Electric propulsion motor";
        doc /* [Source: avenger_v2_5_sysml_v2_ingestion.md:20] */
        attribute interface_item : String = "Three-phase drive from ESC; propeller shaft; temperature telemetry";
        doc /* [unit: kg] [Source: avenger_v2_5_sysml_v2_ingestion.md:20] */
        attribute mass : String = "Not stated";
        doc /* [Source: avenger_v2_5_sysml_v2_ingestion.md:20] */
        attribute part_number : String = "AXI 5345/16 HD GOLD LINE V3";
        doc /* [unit: W] [Source: avenger_v2_5_sysml_v2_ingestion.md:20] */
        attribute power : String = "Not stated";
    }
    doc /* [Source: uav_launcher_pl_40_sysml_v2_ingestion_manual.md:39] */
    part def PL_40_Battery {
        doc /* [Source: uav_launcher_pl_40_sysml_v2_ingestion_manual.md:39] */
        attribute component_name : String = "Makita 18 V Li-Ion 6000 mAh battery, quantity 2";
        doc /* [Source: uav_launcher_pl_40_sysml_v2_ingestion_manual.md:39] */
        attribute interface_item : String = "18 V DC to compressor unit and trigger handle";
        doc /* [unit: kg] [Source: uav_launcher_pl_40_sysml_v2_ingestion_manual.md:39] */
        attribute mass : String = "Not stated";
        doc /* [Source: uav_launcher_pl_40_sysml_v2_ingestion_manual.md:39] */
        attribute part_number : String = "Makita BL1860B";
        doc /* [unit: W] [Source: uav_launcher_pl_40_sysml_v2_ingestion_manual.md:39] */
        attribute power : String = "Not stated";
    }
    doc /* [Source: uav_launcher_pl_40_sysml_v2_ingestion_manual.md:14] */
    part def PL_40_Carriage {
        doc /* [Source: uav_launcher_pl_40_sysml_v2_ingestion_manual.md:14] */
        attribute component_name : String = "Rolling carriage with four support levers";
        doc /* [Source: uav_launcher_pl_40_sysml_v2_ingestion_manual.md:14] */
        attribute interface_item : String = "UAV connection hooks; pulling rope; rail track; safety lock pin";
        doc /* [unit: kg] [Source: uav_launcher_pl_40_sysml_v2_ingestion_manual.md:14] */
        attribute mass : String = "Not stated";
        doc /* [Source: uav_launcher_pl_40_sysml_v2_ingestion_manual.md:14] */
        attribute part_number : String = "Not stated";
        doc /* [unit: W] [Source: uav_launcher_pl_40_sysml_v2_ingestion_manual.md:14] */
        attribute power : String = "Not stated";
    }
    doc /* [Source: uav_launcher_pl_40_sysml_v2_ingestion_manual.md:16] */
    part def PL_40_Carriage_Safety_Lock_Pin {
        doc /* [Source: uav_launcher_pl_40_sysml_v2_ingestion_manual.md:16] */
        attribute component_name : String = "Red-handled carriage safety pin";
        doc /* [Source: uav_launcher_pl_40_sysml_v2_ingestion_manual.md:16] */
        attribute interface_item : String = "Rear launch position lock; removed only before launch";
        doc /* [unit: kg] [Source: uav_launcher_pl_40_sysml_v2_ingestion_manual.md:16] */
        attribute mass : String = "Not stated";
        doc /* [Source: uav_launcher_pl_40_sysml_v2_ingestion_manual.md:16] */
        attribute part_number : String = "Not stated";
        doc /* [unit: W] [Source: uav_launcher_pl_40_sysml_v2_ingestion_manual.md:16] */
        attribute power : String = "Not stated";
    }
    doc /* [Source: uav_launcher_pl_40_sysml_v2_ingestion_manual.md:33] */
    part def PL_40_Compressor {
        doc /* [Source: uav_launcher_pl_40_sysml_v2_ingestion_manual.md:33] */
        attribute component_name : String = "18 V DC air compressor";
        doc /* [Source: uav_launcher_pl_40_sysml_v2_ingestion_manual.md:33] */
        attribute interface_item : String = "Main tank; battery dock; controller";
        doc /* [unit: kg] [Source: uav_launcher_pl_40_sysml_v2_ingestion_manual.md:33] */
        attribute mass : String = "Not stated";
        doc /* [Source: uav_launcher_pl_40_sysml_v2_ingestion_manual.md:33] */
        attribute part_number : String = "Not stated";
        doc /* [unit: W] [Source: uav_launcher_pl_40_sysml_v2_ingestion_manual.md:33] */
        attribute power : String = "Not stated";
    }
    doc /* [Source: uav_launcher_pl_40_sysml_v2_ingestion_manual.md:32, uav_launcher_pl_40_sysml_v2_ingestion_manual.md:124] */
    part def PL_40_Compressor_Unit {
        doc /* [Source: uav_launcher_pl_40_sysml_v2_ingestion_manual.md:32, uav_launcher_pl_40_sysml_v2_ingestion_manual.md:124] */
        attribute component_name : String = "Wheeled compressor case with compressor, tank, controller and valves";
        doc /* [Source: uav_launcher_pl_40_sysml_v2_ingestion_manual.md:32, uav_launcher_pl_40_sysml_v2_ingestion_manual.md:124] */
        attribute interface_item : String = "18 V battery dock; pneumatic outlet; pressure sensor; trigger cable";
        doc /* [unit: kg] [Source: uav_launcher_pl_40_sysml_v2_ingestion_manual.md:32, uav_launcher_pl_40_sysml_v2_ingestion_manual.md:124] */
        attribute mass : Integer = 25;
        doc /* [Source: uav_launcher_pl_40_sysml_v2_ingestion_manual.md:32, uav_launcher_pl_40_sysml_v2_ingestion_manual.md:124] */
        attribute part_number : String = "Not stated";
        doc /* [unit: W] [Source: uav_launcher_pl_40_sysml_v2_ingestion_manual.md:32, uav_launcher_pl_40_sysml_v2_ingestion_manual.md:124] */
        attribute power : String = "Not stated";
    }
    doc /* [Source: uav_launcher_pl_40_sysml_v2_ingestion_manual.md:45] */
    part def PL_40_Connection_Hose {
        doc /* [Source: uav_launcher_pl_40_sysml_v2_ingestion_manual.md:45] */
        attribute component_name : String = "High-pressure hose with cam-lock couplings and securing ring";
        doc /* [Source: uav_launcher_pl_40_sysml_v2_ingestion_manual.md:45] */
        attribute interface_item : String = "Tank-side connector; launcher inlet";
        doc /* [unit: kg] [Source: uav_launcher_pl_40_sysml_v2_ingestion_manual.md:45] */
        attribute mass : String = "Not stated";
        doc /* [Source: uav_launcher_pl_40_sysml_v2_ingestion_manual.md:45] */
        attribute part_number : String = "Not stated";
        doc /* [unit: W] [Source: uav_launcher_pl_40_sysml_v2_ingestion_manual.md:45] */
        attribute power : String = "Not stated";
    }
    doc /* [Source: uav_launcher_pl_40_sysml_v2_ingestion_manual.md:28, uav_launcher_pl_40_sysml_v2_ingestion_manual.md:29, uav_launcher_pl_40_sysml_v2_ingestion_manual.md:30] */
    part def PL_40_Ground_Anchors {
        doc /* [Source: uav_launcher_pl_40_sysml_v2_ingestion_manual.md:28, uav_launcher_pl_40_sysml_v2_ingestion_manual.md:29, uav_launcher_pl_40_sysml_v2_ingestion_manual.md:30] */
        attribute component_name : String = "Three serrated ground anchors with anchor disk and hammer";
        doc /* [Source: uav_launcher_pl_40_sysml_v2_ingestion_manual.md:28, uav_launcher_pl_40_sysml_v2_ingestion_manual.md:29, uav_launcher_pl_40_sysml_v2_ingestion_manual.md:30] */
        attribute interface_item : String = "Rear support leg; soil anchoring";
        doc /* [unit: kg] [Source: uav_launcher_pl_40_sysml_v2_ingestion_manual.md:28, uav_launcher_pl_40_sysml_v2_ingestion_manual.md:29, uav_launcher_pl_40_sysml_v2_ingestion_manual.md:30] */
        attribute mass : String = "Not stated";
        doc /* [Source: uav_launcher_pl_40_sysml_v2_ingestion_manual.md:28, uav_launcher_pl_40_sysml_v2_ingestion_manual.md:29, uav_launcher_pl_40_sysml_v2_ingestion_manual.md:30] */
        attribute part_number : String = "Not stated";
        doc /* [unit: W] [Source: uav_launcher_pl_40_sysml_v2_ingestion_manual.md:28, uav_launcher_pl_40_sysml_v2_ingestion_manual.md:29, uav_launcher_pl_40_sysml_v2_ingestion_manual.md:30] */
        attribute power : String = "Not stated";
    }
    doc /* [Source: uav_launcher_pl_40_sysml_v2_ingestion_manual.md:57] */
    part def PL_40_Hook_Option_A {
        doc /* [Source: uav_launcher_pl_40_sysml_v2_ingestion_manual.md:57] */
        attribute component_name : String = "Front and rear hook brackets, Aluminum 6061-T6";
        doc /* [Source: uav_launcher_pl_40_sysml_v2_ingestion_manual.md:57] */
        attribute interface_item : String = "Carriage support levers";
        doc /* [unit: kg] [Source: uav_launcher_pl_40_sysml_v2_ingestion_manual.md:57] */
        attribute mass : Real = 0.004;
        doc /* [Source: uav_launcher_pl_40_sysml_v2_ingestion_manual.md:57] */
        attribute part_number : String = "Not stated";
        doc /* [unit: W] [Source: uav_launcher_pl_40_sysml_v2_ingestion_manual.md:57] */
        attribute power : String = "Not stated";
    }
    doc /* [Source: uav_launcher_pl_40_sysml_v2_ingestion_manual.md:58] */
    part def PL_40_Hook_Option_B {
        doc /* [Source: uav_launcher_pl_40_sysml_v2_ingestion_manual.md:58] */
        attribute component_name : String = "Single-piece longitudinal hook bar with dual notches";
        doc /* [Source: uav_launcher_pl_40_sysml_v2_ingestion_manual.md:58] */
        attribute interface_item : String = "Carriage support levers";
        doc /* [unit: kg] [Source: uav_launcher_pl_40_sysml_v2_ingestion_manual.md:58] */
        attribute mass : String = "Not stated";
        doc /* [Source: uav_launcher_pl_40_sysml_v2_ingestion_manual.md:58] */
        attribute part_number : String = "Not stated";
        doc /* [unit: W] [Source: uav_launcher_pl_40_sysml_v2_ingestion_manual.md:58] */
        attribute power : String = "Not stated";
    }
    doc /* [Source: uav_launcher_pl_40_sysml_v2_ingestion_manual.md:59] */
    part def PL_40_Hook_Option_C {
        doc /* [Source: uav_launcher_pl_40_sysml_v2_ingestion_manual.md:59] */
        attribute component_name : String = "Threaded M8 flanged launch lugs in AISI 304";
        doc /* [Source: uav_launcher_pl_40_sysml_v2_ingestion_manual.md:59] */
        attribute interface_item : String = "Carriage support levers";
        doc /* [unit: kg] [Source: uav_launcher_pl_40_sysml_v2_ingestion_manual.md:59] */
        attribute mass : String = "Not stated";
        doc /* [Source: uav_launcher_pl_40_sysml_v2_ingestion_manual.md:59] */
        attribute part_number : String = "Not stated";
        doc /* [unit: W] [Source: uav_launcher_pl_40_sysml_v2_ingestion_manual.md:59] */
        attribute power : String = "Not stated";
    }
    doc /* [Source: uav_launcher_pl_40_sysml_v2_ingestion_manual.md:38] */
    part def PL_40_Main_Tank {
        doc /* [Source: uav_launcher_pl_40_sysml_v2_ingestion_manual.md:38] */
        attribute component_name : String = "Compressed air reservoir";
        doc /* [Source: uav_launcher_pl_40_sysml_v2_ingestion_manual.md:38] */
        attribute interface_item : String = "Compressor; outlet valve; release valve; pressure gauge";
        doc /* [unit: kg] [Source: uav_launcher_pl_40_sysml_v2_ingestion_manual.md:38] */
        attribute mass : String = "Not stated";
        doc /* [Source: uav_launcher_pl_40_sysml_v2_ingestion_manual.md:38] */
        attribute part_number : String = "Not stated";
        doc /* [unit: W] [Source: uav_launcher_pl_40_sysml_v2_ingestion_manual.md:38] */
        attribute power : String = "Not stated";
    }
    doc /* [Source: uav_launcher_pl_40_sysml_v2_ingestion_manual.md:53, uav_launcher_pl_40_sysml_v2_ingestion_manual.md:54] */
    part def PL_40_Maintenance_Kits {
        doc /* [Source: uav_launcher_pl_40_sysml_v2_ingestion_manual.md:53, uav_launcher_pl_40_sysml_v2_ingestion_manual.md:54] */
        attribute component_name : String = "Pulling rope replacement kit and carriage wheel bearing replacement kit";
        doc /* [Source: uav_launcher_pl_40_sysml_v2_ingestion_manual.md:53, uav_launcher_pl_40_sysml_v2_ingestion_manual.md:54] */
        attribute interface_item : String = "Maintenance only";
        doc /* [unit: kg] [Source: uav_launcher_pl_40_sysml_v2_ingestion_manual.md:53, uav_launcher_pl_40_sysml_v2_ingestion_manual.md:54] */
        attribute mass : String = "Not stated";
        doc /* [Source: uav_launcher_pl_40_sysml_v2_ingestion_manual.md:53, uav_launcher_pl_40_sysml_v2_ingestion_manual.md:54] */
        attribute part_number : String = "Not stated";
        doc /* [unit: W] [Source: uav_launcher_pl_40_sysml_v2_ingestion_manual.md:53, uav_launcher_pl_40_sysml_v2_ingestion_manual.md:54] */
        attribute power : String = "Not stated";
    }
    doc /* [Source: uav_launcher_pl_40_sysml_v2_ingestion_manual.md:43] */
    part def PL_40_Power_Switching_Circuit {
        doc /* [Source: uav_launcher_pl_40_sysml_v2_ingestion_manual.md:43] */
        attribute component_name : String = "Electronic controller with pressure and battery protection";
        doc /* [Source: uav_launcher_pl_40_sysml_v2_ingestion_manual.md:43] */
        attribute interface_item : String = "Pressure sensor; valves; battery; SET and PWR LEDs";
        doc /* [unit: kg] [Source: uav_launcher_pl_40_sysml_v2_ingestion_manual.md:43] */
        attribute mass : String = "Not stated";
        doc /* [Source: uav_launcher_pl_40_sysml_v2_ingestion_manual.md:43] */
        attribute part_number : String = "Not stated";
        doc /* [unit: W] [Source: uav_launcher_pl_40_sysml_v2_ingestion_manual.md:43] */
        attribute power : String = "Not stated";
    }
    doc /* [Source: uav_launcher_pl_40_sysml_v2_ingestion_manual.md:40] */
    part def PL_40_Pressure_Gauge {
        doc /* [Source: uav_launcher_pl_40_sysml_v2_ingestion_manual.md:40] */
        attribute component_name : String = "Analog pressure manometer";
        doc /* [Source: uav_launcher_pl_40_sysml_v2_ingestion_manual.md:40] */
        attribute interface_item : String = "Main tank pressure indication";
        doc /* [unit: kg] [Source: uav_launcher_pl_40_sysml_v2_ingestion_manual.md:40] */
        attribute mass : String = "Not stated";
        doc /* [Source: uav_launcher_pl_40_sysml_v2_ingestion_manual.md:40] */
        attribute part_number : String = "Not stated";
        doc /* [unit: W] [Source: uav_launcher_pl_40_sysml_v2_ingestion_manual.md:40] */
        attribute power : String = "Not stated";
    }
    doc /* [Source: uav_launcher_pl_40_sysml_v2_ingestion_manual.md:13] */
    part def PL_40_Pulling_Rope {
        doc /* [Source: uav_launcher_pl_40_sysml_v2_ingestion_manual.md:13] */
        attribute component_name : String = "High-strength pulling rope from piston to carriage";
        doc /* [Source: uav_launcher_pl_40_sysml_v2_ingestion_manual.md:13] */
        attribute interface_item : String = "Internal piston; roller block; carriage; replaced every 100 launches";
        doc /* [unit: kg] [Source: uav_launcher_pl_40_sysml_v2_ingestion_manual.md:13] */
        attribute mass : String = "Not stated";
        doc /* [Source: uav_launcher_pl_40_sysml_v2_ingestion_manual.md:13] */
        attribute part_number : String = "Not stated";
        doc /* [unit: W] [Source: uav_launcher_pl_40_sysml_v2_ingestion_manual.md:13] */
        attribute power : String = "Not stated";
    }
    doc /* [Source: uav_launcher_pl_40_sysml_v2_ingestion_manual.md:7, uav_launcher_pl_40_sysml_v2_ingestion_manual.md:119, uav_launcher_pl_40_sysml_v2_ingestion_manual.md:122] */
    part def PL_40_Rail {
        doc /* [Source: uav_launcher_pl_40_sysml_v2_ingestion_manual.md:7, uav_launcher_pl_40_sysml_v2_ingestion_manual.md:119, uav_launcher_pl_40_sysml_v2_ingestion_manual.md:122] */
        attribute component_name : String = "UAV pneumatic launcher rail assembly";
        doc /* [Source: uav_launcher_pl_40_sysml_v2_ingestion_manual.md:7, uav_launcher_pl_40_sysml_v2_ingestion_manual.md:119, uav_launcher_pl_40_sysml_v2_ingestion_manual.md:122] */
        attribute interface_item : String = "Pneumatic inlet; rail clamps; carriage track; front and rear support legs";
        doc /* [unit: kg] [Source: uav_launcher_pl_40_sysml_v2_ingestion_manual.md:7, uav_launcher_pl_40_sysml_v2_ingestion_manual.md:119, uav_launcher_pl_40_sysml_v2_ingestion_manual.md:122] */
        attribute mass : Integer = 68;
        doc /* [Source: uav_launcher_pl_40_sysml_v2_ingestion_manual.md:7, uav_launcher_pl_40_sysml_v2_ingestion_manual.md:119, uav_launcher_pl_40_sysml_v2_ingestion_manual.md:122] */
        attribute part_number : String = "PL-40";
        doc /* [unit: W] [Source: uav_launcher_pl_40_sysml_v2_ingestion_manual.md:7, uav_launcher_pl_40_sysml_v2_ingestion_manual.md:119, uav_launcher_pl_40_sysml_v2_ingestion_manual.md:122] */
        attribute power : String = "Not stated";
    }
    doc /* [Source: uav_launcher_pl_40_sysml_v2_ingestion_manual.md:8] */
    part def PL_40_Rail_Module_RAIL_1 {
        doc /* [Source: uav_launcher_pl_40_sysml_v2_ingestion_manual.md:8] */
        attribute component_name : String = "Rear rail module";
        doc /* [Source: uav_launcher_pl_40_sysml_v2_ingestion_manual.md:8] */
        attribute interface_item : String = "Carriage initial position; safety lock; rear support leg";
        doc /* [unit: kg] [Source: uav_launcher_pl_40_sysml_v2_ingestion_manual.md:8] */
        attribute mass : String = "Not stated";
        doc /* [Source: uav_launcher_pl_40_sysml_v2_ingestion_manual.md:8] */
        attribute part_number : String = "RAIL 1";
        doc /* [unit: W] [Source: uav_launcher_pl_40_sysml_v2_ingestion_manual.md:8] */
        attribute power : String = "Not stated";
    }
    doc /* [Source: uav_launcher_pl_40_sysml_v2_ingestion_manual.md:10] */
    part def PL_40_Rail_Module_RAIL_2 {
        doc /* [Source: uav_launcher_pl_40_sysml_v2_ingestion_manual.md:10] */
        attribute component_name : String = "Middle rail module";
        doc /* [Source: uav_launcher_pl_40_sysml_v2_ingestion_manual.md:10] */
        attribute interface_item : String = "Toggle clamps; O-ring seals; end plates";
        doc /* [unit: kg] [Source: uav_launcher_pl_40_sysml_v2_ingestion_manual.md:10] */
        attribute mass : String = "Not stated";
        doc /* [Source: uav_launcher_pl_40_sysml_v2_ingestion_manual.md:10] */
        attribute part_number : String = "RAIL 2";
        doc /* [unit: W] [Source: uav_launcher_pl_40_sysml_v2_ingestion_manual.md:10] */
        attribute power : String = "Not stated";
    }
    doc /* [Source: uav_launcher_pl_40_sysml_v2_ingestion_manual.md:11] */
    part def PL_40_Rail_Module_RAIL_3 {
        doc /* [Source: uav_launcher_pl_40_sysml_v2_ingestion_manual.md:11] */
        attribute component_name : String = "Front rail module with internal piston and inlet port";
        doc /* [Source: uav_launcher_pl_40_sysml_v2_ingestion_manual.md:11] */
        attribute interface_item : String = "Piston; pulling rope; roller block; front legs; air inlet";
        doc /* [unit: kg] [Source: uav_launcher_pl_40_sysml_v2_ingestion_manual.md:11] */
        attribute mass : String = "Not stated";
        doc /* [Source: uav_launcher_pl_40_sysml_v2_ingestion_manual.md:11] */
        attribute part_number : String = "RAIL 3";
        doc /* [unit: W] [Source: uav_launcher_pl_40_sysml_v2_ingestion_manual.md:11] */
        attribute power : String = "Not stated";
    }
    doc /* [Source: uav_launcher_pl_40_sysml_v2_ingestion_manual.md:35] */
    part def PL_40_Remote_Release_Valve {
        doc /* [Source: uav_launcher_pl_40_sysml_v2_ingestion_manual.md:35] */
        attribute component_name : String = "Main launch release valve";
        doc /* [Source: uav_launcher_pl_40_sysml_v2_ingestion_manual.md:35] */
        attribute interface_item : String = "Main tank; launcher inlet; trigger handle";
        doc /* [unit: kg] [Source: uav_launcher_pl_40_sysml_v2_ingestion_manual.md:35] */
        attribute mass : String = "Not stated";
        doc /* [Source: uav_launcher_pl_40_sysml_v2_ingestion_manual.md:35] */
        attribute part_number : String = "Not stated";
        doc /* [unit: W] [Source: uav_launcher_pl_40_sysml_v2_ingestion_manual.md:35] */
        attribute power : String = "Not stated";
    }
    doc /* [Source: uav_launcher_pl_40_sysml_v2_ingestion_manual.md:52] */
    part def PL_40_Transport_Case {
        doc /* [Source: uav_launcher_pl_40_sysml_v2_ingestion_manual.md:52] */
        attribute component_name : String = "Wheeled hard case for the rail set";
        doc /* [Source: uav_launcher_pl_40_sysml_v2_ingestion_manual.md:52] */
        attribute interface_item : String = "Loaded rail transport";
        doc /* [unit: kg] [Source: uav_launcher_pl_40_sysml_v2_ingestion_manual.md:52] */
        attribute mass : Integer = 43;
        doc /* [Source: uav_launcher_pl_40_sysml_v2_ingestion_manual.md:52] */
        attribute part_number : String = "Not stated";
        doc /* [unit: W] [Source: uav_launcher_pl_40_sysml_v2_ingestion_manual.md:52] */
        attribute power : String = "Not stated";
    }
    doc /* [Source: uav_launcher_pl_40_sysml_v2_ingestion_manual.md:47] */
    part def PL_40_Trigger_Handle {
        doc /* [Source: uav_launcher_pl_40_sysml_v2_ingestion_manual.md:47] */
        attribute component_name : String = "Handheld remote launch controller with two switches and safety levers";
        doc /* [Source: uav_launcher_pl_40_sysml_v2_ingestion_manual.md:47] */
        attribute interface_item : String = "18 V battery dock; control cable; remote release valve";
        doc /* [unit: kg] [Source: uav_launcher_pl_40_sysml_v2_ingestion_manual.md:47] */
        attribute mass : String = "Not stated";
        doc /* [Source: uav_launcher_pl_40_sysml_v2_ingestion_manual.md:47] */
        attribute part_number : String = "Not stated";
        doc /* [unit: W] [Source: uav_launcher_pl_40_sysml_v2_ingestion_manual.md:47] */
        attribute power : String = "Not stated";
    }
    doc /* [Source: avenger_v2_5_sysml_v2_ingestion.md:40, a5-user-manual-2.md:262, a5-user-manual-2.md:314] */
    part def Parachute_Deployment_Non_Mission {
        doc /* [Source: avenger_v2_5_sysml_v2_ingestion.md:40, a5-user-manual-2.md:262, a5-user-manual-2.md:314] */
        attribute component_name : String = "Parachute deployment module, non-mission R&D variant, configuration: non-mission; baseline: false";
        doc /* [Source: avenger_v2_5_sysml_v2_ingestion.md:40, a5-user-manual-2.md:262, a5-user-manual-2.md:314] */
        attribute interface_item : String = "Two 50 V igniter outputs; excluded from mission baseline analysis";
        doc /* [unit: kg] [Source: avenger_v2_5_sysml_v2_ingestion.md:40, a5-user-manual-2.md:262, a5-user-manual-2.md:314] */
        attribute mass : String = "Not stated";
        doc /* [Source: avenger_v2_5_sysml_v2_ingestion.md:40, a5-user-manual-2.md:262, a5-user-manual-2.md:314] */
        attribute part_number : String = "Not stated";
        doc /* [unit: W] [Source: avenger_v2_5_sysml_v2_ingestion.md:40, a5-user-manual-2.md:262, a5-user-manual-2.md:314] */
        attribute power : String = "Not stated";
    }
    doc /* [Source: avenger_v2_5_sysml_v2_ingestion.md:41, avenger_v2_5_sysml_v2_ingestion.md:168] */
    part def Parachute_Igniter_1 {
        doc /* [Source: avenger_v2_5_sysml_v2_ingestion.md:41, avenger_v2_5_sysml_v2_ingestion.md:168] */
        attribute component_name : String = "Upper pyrotechnic igniter for payload bay cover retention wire";
        doc /* [Source: avenger_v2_5_sysml_v2_ingestion.md:41, avenger_v2_5_sysml_v2_ingestion.md:168] */
        attribute interface_item : String = "50 V power from EPS";
        doc /* [unit: kg] [Source: avenger_v2_5_sysml_v2_ingestion.md:41, avenger_v2_5_sysml_v2_ingestion.md:168] */
        attribute mass : String = "Not stated";
        doc /* [Source: avenger_v2_5_sysml_v2_ingestion.md:41, avenger_v2_5_sysml_v2_ingestion.md:168] */
        attribute part_number : String = "Not stated";
        doc /* [unit: W] [Source: avenger_v2_5_sysml_v2_ingestion.md:41, avenger_v2_5_sysml_v2_ingestion.md:168] */
        attribute power : String = "Not stated";
    }
    doc /* [Source: avenger_v2_5_sysml_v2_ingestion.md:42, avenger_v2_5_sysml_v2_ingestion.md:168] */
    part def Parachute_Igniter_2 {
        doc /* [Source: avenger_v2_5_sysml_v2_ingestion.md:42, avenger_v2_5_sysml_v2_ingestion.md:168] */
        attribute component_name : String = "Lower pyrotechnic igniter for payload bay cover retention wire";
        doc /* [Source: avenger_v2_5_sysml_v2_ingestion.md:42, avenger_v2_5_sysml_v2_ingestion.md:168] */
        attribute interface_item : String = "50 V power from EPS";
        doc /* [unit: kg] [Source: avenger_v2_5_sysml_v2_ingestion.md:42, avenger_v2_5_sysml_v2_ingestion.md:168] */
        attribute mass : String = "Not stated";
        doc /* [Source: avenger_v2_5_sysml_v2_ingestion.md:42, avenger_v2_5_sysml_v2_ingestion.md:168] */
        attribute part_number : String = "Not stated";
        doc /* [unit: W] [Source: avenger_v2_5_sysml_v2_ingestion.md:42, avenger_v2_5_sysml_v2_ingestion.md:168] */
        attribute power : String = "Not stated";
    }
    doc /* Synthesized system component for Parametric_Limits_Table */
    part def Parametric_Limits_Table_System {
        doc /* [unit: m/s] */
        attribute PL_01 : Real;
        doc /* [unit: m/s] */
        attribute PL_02 : Real;
        doc /* [unit: m/s] */
        attribute PL_03 : Real;
        doc /* [unit: deg] */
        attribute PL_04 : Real;
        doc /* [unit: m/s] */
        attribute PL_05 : Real;
        doc /* [unit: min] */
        attribute PL_06 : Real;
        doc /* [unit: km] */
        attribute PL_07 : Real;
        doc /* [unit: km] */
        attribute PL_08 : Real;
        doc /* [unit: m] */
        attribute PL_09 : Real;
        doc /* [unit: m] */
        attribute PL_10 : Real;
        doc /* [unit: m] */
        attribute PL_11 : Real;
        doc /* [unit: kg] */
        attribute PL_12 : Real;
        doc /* [unit: kg] */
        attribute PL_13 : Real;
        doc /* [unit: units] */
        attribute PL_14 : Real;
        doc /* [unit: units] */
        attribute PL_15 : Real;
        doc /* [unit: units] */
        attribute PL_16 : Real;
        doc /* [unit: units] */
        attribute PL_17 : Real;
        doc /* [unit: units] */
        attribute PL_18 : Real;
        doc /* [unit: cm] */
        attribute PL_19 : Real;
        doc /* [unit: cm] */
        attribute PL_20 : Real;
        doc /* [unit: cm] */
        attribute PL_21 : Real;
        doc /* [unit: V] */
        attribute PL_22 : Real;
        doc /* [unit: V] */
        attribute PL_23 : Real;
        doc /* [unit: V] */
        attribute PL_24 : Real;
        doc /* [unit: deg] */
        attribute PL_25 : Real;
        doc /* [unit: deg] */
        attribute PL_26 : Real;
        doc /* [unit: X] */
        attribute PL_27 : Real;
        doc /* [unit: pixels] */
        attribute PL_28 : Real;
        doc /* [unit: pixels] */
        attribute PL_29 : Real;
        doc /* [unit: pixels] */
        attribute PL_30 : Real;
        doc /* [unit: pixels] */
        attribute PL_31 : Real;
        doc /* [unit: V] */
        attribute PL_32 : Real;
        doc /* [unit: V] */
        attribute PL_33 : Real;
        doc /* [unit: m/s] */
        attribute PL_34 : Real;
        doc /* [unit: m/s] */
        attribute PL_35 : Real;
        doc /* [unit: m] */
        attribute PL_36 : Real;
        doc /* [unit: m] */
        attribute PL_37 : Real;
        doc /* [unit: chars] */
        attribute PL_38 : Real;
        doc /* [unit: W] */
        attribute PL_39 : Real;
        doc /* [unit: bar] */
        attribute PL_40 : Real;
        doc /* [unit: bar] */
        attribute PL_41 : Real;
        doc /* [unit: s] */
        attribute PL_42 : Real;
        doc /* [unit: s] */
        attribute PL_43 : Real;
        doc /* [unit: deg] */
        attribute PL_44 : Real;
        doc /* [unit: m/s] */
        attribute PL_45 : Real;
        doc /* [unit: V] */
        attribute PL_46 : Real;
        doc /* [unit: V] */
        attribute PL_47 : Real;
        doc /* [unit: V] */
        attribute PL_48 : Real;
        doc /* [unit: Ohm] */
        attribute PL_49 : Real;
        doc /* [unit: mA] */
        attribute PL_50 : Real;
        doc /* [unit: VDC] */
        attribute PL_51 : Real;
        doc /* [unit: VDC] */
        attribute PL_52 : Real;
        doc /* [unit: VDC] */
        attribute PL_53 : Real;
        doc /* [unit: ms] */
        attribute PL_54 : Real;
        doc /* [unit: percent] */
        attribute PL_55 : Real;
        doc /* [unit: bps] */
        attribute PL_56 : Real;
        doc /* [unit: Hz] */
        attribute PL_57 : Real;
        doc /* [unit: ms] */
        attribute PL_58 : Real;
        doc /* [unit: ms] */
        attribute PL_59 : Real;
        doc /* [unit: V] */
        attribute PL_60 : Real;
        doc /* [unit: bytes] */
        attribute PL_61 : Real;
        doc /* [unit: bytes] */
        attribute PL_62 : Real;
        doc /* [unit: g] */
        attribute PL_63 : Real;
        doc /* [unit: kg] */
        attribute PL_64 : Real;
        doc /* [unit: m/s] */
        attribute PL_65 : Real;
        doc /* [unit: deg] */
        attribute PL_66 : Real;
        doc /* [unit: bar] */
        attribute PL_67 : Real;
        doc /* [unit: bar] */
        attribute PL_68 : Real;
        doc /* [unit: kg] */
        attribute PL_69 : Real;
        doc /* [unit: kg] */
        attribute PL_70 : Real;
        doc /* [unit: kg] */
        attribute PL_71 : Real;
        doc /* [unit: min] */
        attribute PL_72 : Real;
        doc /* [unit: degC] */
        attribute PL_73 : Real;
        doc /* [unit: degC] */
        attribute PL_74 : Real;
        doc /* [unit: V] */
        attribute PL_75 : Real;
        doc /* [unit: mAh] */
        attribute PL_76 : Real;
        doc /* [unit: V] */
        attribute PL_77 : Real;
        doc /* [unit: V] */
        attribute PL_78 : Real;
        doc /* [unit: s] */
        attribute PL_79 : Real;
        doc /* [unit: launches] */
        attribute PL_80 : Real;
        doc /* [unit: mm] */
        attribute PL_81 : Real;
        doc /* [unit: mm] */
        attribute PL_82 : Real;
        doc /* [unit: mm] */
        attribute PL_83 : Real;
        doc /* [unit: mm] */
        attribute PL_84 : Real;
        doc /* [unit: mm] */
        attribute PL_85 : Real;
        doc /* [unit: mm] */
        attribute PL_86 : Real;
        doc /* [unit: mm] */
        attribute PL_87 : Real;
        doc /* [unit: s] */
        attribute PL_88 : Real;
        doc /* [unit: min] */
        attribute PL_89 : Real;
        doc /* [unit: min] */
        attribute PL_90 : Real;
        doc /* [unit: degC] */
        attribute PL_91 : Real;
        doc /* [unit: degC] */
        attribute PL_92 : Real;
        doc /* [unit: m] */
        attribute PL_93 : Real;
        doc /* [unit: m] */
        attribute PL_94 : Real;
        doc /* [unit: m/s] */
        assert constraint assert_PL_01_range {
            PL_01 >= 30 and PL_01 <= 30;
        }
        doc /* [unit: m/s] */
        assert constraint assert_PL_02_range {
            PL_02 <= 38;
        }
        doc /* [unit: m/s] */
        assert constraint assert_PL_03_range {
            PL_03 <= 55;
        }
        doc /* [unit: deg] */
        assert constraint assert_PL_04_range {
            PL_04 <= 22;
        }
        doc /* [unit: m/s] */
        assert constraint assert_PL_05_range {
            PL_05 >= 26;
        }
        doc /* [unit: min] */
        assert constraint assert_PL_06_range {
            PL_06 >= 0 and PL_06 <= 90;
        }
        doc /* [unit: km] */
        assert constraint assert_PL_07_range {
            PL_07 >= 0 and PL_07 <= 60;
        }
        doc /* [unit: km] */
        assert constraint assert_PL_08_range {
            PL_08 >= 60 and PL_08 <= 180;
        }
        doc /* [unit: m] */
        assert constraint assert_PL_09_range {
            PL_09 >= 1.8 and PL_09 <= 1.8;
        }
        doc /* [unit: m] */
        assert constraint assert_PL_10_range {
            PL_10 >= 1.6 and PL_10 <= 1.6;
        }
        doc /* [unit: m] */
        assert constraint assert_PL_11_range {
            PL_11 >= 1.1 and PL_11 <= 1.1;
        }
        doc /* [unit: kg] */
        assert constraint assert_PL_12_range {
            PL_12 <= 17;
        }
        doc /* [unit: kg] */
        assert constraint assert_PL_13_range {
            PL_13 <= 5;
        }
        doc /* [unit: units] */
        assert constraint assert_PL_14_range {
            PL_14 >= 4 and PL_14 <= 4;
        }
        doc /* [unit: units] */
        assert constraint assert_PL_15_range {
            PL_15 >= 4 and PL_15 <= 4;
        }
        doc /* [unit: units] */
        assert constraint assert_PL_16_range {
            PL_16 >= 4 and PL_16 <= 4;
        }
        doc /* [unit: units] */
        assert constraint assert_PL_17_range {
            PL_17 >= 4 and PL_17 <= 4;
        }
        doc /* [unit: units] */
        assert constraint assert_PL_18_range {
            PL_18 >= 8 and PL_18 <= 8;
        }
        doc /* [unit: cm] */
        assert constraint assert_PL_19_range {
            PL_19 >= 970 and PL_19 <= 970;
        }
        doc /* [unit: cm] */
        assert constraint assert_PL_20_range {
            PL_20 >= 150 and PL_20 <= 150;
        }
        doc /* [unit: cm] */
        assert constraint assert_PL_21_range {
            PL_21 >= 120 and PL_21 <= 120;
        }
        doc /* [unit: V] */
        assert constraint assert_PL_22_range {
            PL_22 >= 8 and PL_22 <= 8;
        }
        doc /* [unit: V] */
        assert constraint assert_PL_23_range {
            PL_23 >= 36 and PL_23 <= 36;
        }
        doc /* [unit: V] */
        assert constraint assert_PL_24_range {
            PL_24 >= 50.4 and PL_24 <= 50.4;
        }
        doc /* [unit: deg] */
        assert constraint assert_PL_25_range {
            PL_25 >= -45 and PL_25 <= 135;
        }
        doc /* [unit: deg] */
        assert constraint assert_PL_26_range {
            PL_26 >= -165 and PL_26 <= 165;
        }
        doc /* [unit: X] */
        assert constraint assert_PL_27_range {
            PL_27 >= 1 and PL_27 <= 40;
        }
        doc /* [unit: pixels] */
        assert constraint assert_PL_28_range {
            PL_28 >= 1280 and PL_28 <= 1280;
        }
        doc /* [unit: pixels] */
        assert constraint assert_PL_29_range {
            PL_29 >= 720 and PL_29 <= 720;
        }
        doc /* [unit: pixels] */
        assert constraint assert_PL_30_range {
            PL_30 >= 1280 and PL_30 <= 1280;
        }
        doc /* [unit: pixels] */
        assert constraint assert_PL_31_range {
            PL_31 >= 720 and PL_31 <= 720;
        }
        doc /* [unit: V] */
        assert constraint assert_PL_32_range {
            PL_32 >= 49 and PL_32 <= 49;
        }
        doc /* [unit: V] */
        assert constraint assert_PL_33_range {
            PL_33 >= 50 and PL_33 <= 50;
        }
        doc /* [unit: m/s] */
        assert constraint assert_PL_34_range {
            PL_34 >= 0 and PL_34 <= 3;
        }
        doc /* [unit: m/s] */
        assert constraint assert_PL_35_range {
            PL_35 >= 10;
        }
        doc /* [unit: m] */
        assert constraint assert_PL_36_range {
            PL_36 >= 50;
        }
        doc /* [unit: m] */
        assert constraint assert_PL_37_range {
            PL_37 >= 300 and PL_37 <= 300;
        }
        doc /* [unit: chars] */
        assert constraint assert_PL_38_range {
            PL_38 >= 0 and PL_38 <= 24;
        }
        doc /* [unit: W] */
        assert constraint assert_PL_39_range {
            PL_39 >= 2 and PL_39 <= 2;
        }
        doc /* [unit: bar] */
        assert constraint assert_PL_40_range {
            PL_40 >= 13 and PL_40 <= 13;
        }
        doc /* [unit: bar] */
        assert constraint assert_PL_41_range {
            PL_41 >= 14 and PL_41 <= 14;
        }
        doc /* [unit: s] */
        assert constraint assert_PL_42_range {
            PL_42 >= 2 and PL_42 <= 2;
        }
        doc /* [unit: s] */
        assert constraint assert_PL_43_range {
            PL_43 >= 5 and PL_43 <= 5;
        }
        doc /* [unit: deg] */
        assert constraint assert_PL_44_range {
            PL_44 <= 15;
        }
        doc /* [unit: m/s] */
        assert constraint assert_PL_45_range {
            PL_45 <= 55;
        }
        doc /* [unit: V] */
        assert constraint assert_PL_46_range {
            PL_46 >= 14 and PL_46 <= 14;
        }
        doc /* [unit: V] */
        assert constraint assert_PL_47_range {
            PL_47 >= 32 and PL_47 <= 32;
        }
        doc /* [unit: V] */
        assert constraint assert_PL_48_range {
            PL_48 >= 28 and PL_48 <= 28;
        }
        doc /* [unit: Ohm] */
        assert constraint assert_PL_49_range {
            PL_49 >= 0 and PL_49 <= 0.5;
        }
        doc /* [unit: mA] */
        assert constraint assert_PL_50_range {
            PL_50 >= 20 and PL_50 <= 20;
        }
        doc /* [unit: VDC] */
        assert constraint assert_PL_51_range {
            PL_51 >= 0 and PL_51 <= 0.7;
        }
        doc /* [unit: VDC] */
        assert constraint assert_PL_52_range {
            PL_52 >= 2.5 and PL_52 <= 2.5;
        }
        doc /* [unit: VDC] */
        assert constraint assert_PL_53_range {
            PL_53 >= 3.3 and PL_53 <= 3.3;
        }
        doc /* [unit: ms] */
        assert constraint assert_PL_54_range {
            PL_54 >= 1 and PL_54 <= 1;
        }
        doc /* [unit: percent] */
        assert constraint assert_PL_55_range {
            PL_55 >= 50 and PL_55 <= 50;
        }
        doc /* [unit: bps] */
        assert constraint assert_PL_56_range {
            PL_56 >= 115200 and PL_56 <= 115200;
        }
        doc /* [unit: Hz] */
        assert constraint assert_PL_57_range {
            PL_57 >= 100 and PL_57 <= 100;
        }
        doc /* [unit: ms] */
        assert constraint assert_PL_58_range {
            PL_58 >= 0 and PL_58 <= 5;
        }
        doc /* [unit: ms] */
        assert constraint assert_PL_59_range {
            PL_59 >= 0 and PL_59 <= 10;
        }
        doc /* [unit: V] */
        assert constraint assert_PL_60_range {
            PL_60 >= 0 and PL_60 <= 1800;
        }
        doc /* [unit: bytes] */
        assert constraint assert_PL_61_range {
            PL_61 >= 5 and PL_61 <= 5;
        }
        doc /* [unit: bytes] */
        assert constraint assert_PL_62_range {
            PL_62 >= 14 and PL_62 <= 14;
        }
        doc /* [unit: g] */
        assert constraint assert_PL_63_range {
            PL_63 >= 0.0039 and PL_63 <= 0.0039;
        }
        doc /* [unit: kg] */
        assert constraint assert_PL_64_range {
            PL_64 <= 30;
        }
        doc /* [unit: m/s] */
        assert constraint assert_PL_65_range {
            PL_65 <= 25;
        }
        doc /* [unit: deg] */
        assert constraint assert_PL_66_range {
            PL_66 >= 12 and PL_66 <= 12;
        }
        doc /* [unit: bar] */
        assert constraint assert_PL_67_range {
            PL_67 <= 14;
        }
        doc /* [unit: bar] */
        assert constraint assert_PL_68_range {
            PL_68 <= 16;
        }
        doc /* [unit: kg] */
        assert constraint assert_PL_69_range {
            PL_69 >= 68 and PL_69 <= 68;
        }
        doc /* [unit: kg] */
        assert constraint assert_PL_70_range {
            PL_70 >= 43 and PL_70 <= 43;
        }
        doc /* [unit: kg] */
        assert constraint assert_PL_71_range {
            PL_71 >= 25 and PL_71 <= 25;
        }
        doc /* [unit: min] */
        assert constraint assert_PL_72_range {
            PL_72 >= 0 and PL_72 <= 5;
        }
        doc /* [unit: degC] */
        assert constraint assert_PL_73_range {
            PL_73 >= -20 and PL_73 <= -20;
        }
        doc /* [unit: degC] */
        assert constraint assert_PL_74_range {
            PL_74 >= 50 and PL_74 <= 50;
        }
        doc /* [unit: V] */
        assert constraint assert_PL_75_range {
            PL_75 >= 18 and PL_75 <= 18;
        }
        doc /* [unit: mAh] */
        assert constraint assert_PL_76_range {
            PL_76 >= 6000 and PL_76 <= 6000;
        }
        doc /* [unit: V] */
        assert constraint assert_PL_77_range {
            PL_77 <= 14.5;
        }
        doc /* [unit: V] */
        assert constraint assert_PL_78_range {
            PL_78 >= 16;
        }
        doc /* [unit: s] */
        assert constraint assert_PL_79_range {
            PL_79 >= 5 and PL_79 <= 5;
        }
        doc /* [unit: launches] */
        assert constraint assert_PL_80_range {
            PL_80 <= 100;
        }
        doc /* [unit: mm] */
        assert constraint assert_PL_81_range {
            PL_81 >= 271 and PL_81 <= 271;
        }
        doc /* [unit: mm] */
        assert constraint assert_PL_82_range {
            PL_82 >= 206.5 and PL_82 <= 206.5;
        }
        doc /* [unit: mm] */
        assert constraint assert_PL_83_range {
            PL_83 >= 232.5 and PL_83 <= 232.5;
        }
        doc /* [unit: mm] */
        assert constraint assert_PL_84_range {
            PL_84 >= 0 and PL_84 <= 200;
        }
        doc /* [unit: mm] */
        assert constraint assert_PL_85_range {
            PL_85 >= 0 and PL_85 <= 100;
        }
        doc /* [unit: mm] */
        assert constraint assert_PL_86_range {
            PL_86 >= 1115 and PL_86 <= 1115;
        }
        doc /* [unit: mm] */
        assert constraint assert_PL_87_range {
            PL_87 >= 602 and PL_87 <= 602;
        }
        doc /* [unit: s] */
        assert constraint assert_PL_88_range {
            PL_88 >= 2;
        }
        doc /* [unit: min] */
        assert constraint assert_PL_89_range {
            PL_89 >= 0 and PL_89 <= 55;
        }
        doc /* [unit: min] */
        assert constraint assert_PL_90_range {
            PL_90 >= 0 and PL_90 <= 130;
        }
        doc /* [unit: degC] */
        assert constraint assert_PL_91_range {
            PL_91 >= 10 and PL_91 <= 10;
        }
        doc /* [unit: degC] */
        assert constraint assert_PL_92_range {
            PL_92 >= 40 and PL_92 <= 40;
        }
        doc /* [unit: m] */
        assert constraint assert_PL_93_range {
            PL_93 >= 5 and PL_93 <= 5;
        }
        doc /* [unit: m] */
        assert constraint assert_PL_94_range {
            PL_94 >= 1.28 and PL_94 <= 1.28;
        }
    }
    doc /* [Source: avenger_v2_5_sysml_v2_ingestion.md:32] */
    part def Pitot_Tube_CUAV_SKYE2 {
        doc /* [Source: avenger_v2_5_sysml_v2_ingestion.md:32] */
        attribute component_name : String = "Heated and drained airspeed sensor";
        doc /* [Source: avenger_v2_5_sysml_v2_ingestion.md:32] */
        attribute interface_item : String = "Pneumatic pressure port; pitot power from EPS; CAN 2 continuation";
        doc /* [unit: kg] [Source: avenger_v2_5_sysml_v2_ingestion.md:32] */
        attribute mass : String = "Not stated";
        doc /* [Source: avenger_v2_5_sysml_v2_ingestion.md:32] */
        attribute part_number : String = "CUAV SKYE2";
        doc /* [unit: W] [Source: avenger_v2_5_sysml_v2_ingestion.md:32] */
        attribute power : String = "Not stated";
    }
    doc /* [Source: avenger_v2_5_sysml_v2_ingestion.md:18] */
    part def Power_Meter {
        doc /* [Source: avenger_v2_5_sysml_v2_ingestion.md:18] */
        attribute component_name : String = "Voltage and current sensor with main power switch";
        doc /* [Source: avenger_v2_5_sysml_v2_ingestion.md:18] */
        attribute interface_item : String = "Battery power input; switched power to ESC; CAN 1; UAV RBF key";
        doc /* [unit: kg] [Source: avenger_v2_5_sysml_v2_ingestion.md:18] */
        attribute mass : String = "Not stated";
        doc /* [Source: avenger_v2_5_sysml_v2_ingestion.md:18] */
        attribute part_number : String = "Not stated";
        doc /* [unit: W] [Source: avenger_v2_5_sysml_v2_ingestion.md:18] */
        attribute power : String = "Not stated";
    }
    doc /* [Source: avenger_v2_5_sysml_v2_ingestion.md:15] */
    part def Propulsion {
        doc /* [Source: avenger_v2_5_sysml_v2_ingestion.md:15] */
        attribute component_name : String = "Propulsion subsystem boundary enclosing fuse, power meter, ESC and motor";
        doc /* [Source: avenger_v2_5_sysml_v2_ingestion.md:15] */
        attribute interface_item : String = "Battery main power; three-phase motor drive; ESC telemetry";
        doc /* [unit: kg] [Source: avenger_v2_5_sysml_v2_ingestion.md:15] */
        attribute mass : String = "Not stated";
        doc /* [Source: avenger_v2_5_sysml_v2_ingestion.md:15] */
        attribute part_number : String = "Not stated";
        doc /* [unit: W] [Source: avenger_v2_5_sysml_v2_ingestion.md:15] */
        attribute power : String = "Not stated";
    }
    doc /* [Source: a5-user-manual-2.md:274, a5-prep-and-safety-rev7.md:262] */
    part def Propulsion_Folding_Propeller {
        doc /* [Source: a5-user-manual-2.md:274, a5-prep-and-safety-rev7.md:262] */
        attribute component_name : String = "Folding propeller assembly with two blades";
        doc /* [Source: a5-user-manual-2.md:274, a5-prep-and-safety-rev7.md:262] */
        attribute interface_item : String = "Motor shaft; blades fold rearward toward the tail";
        doc /* [unit: kg] [Source: a5-user-manual-2.md:274, a5-prep-and-safety-rev7.md:262] */
        attribute mass : String = "Not stated";
        doc /* [Source: a5-user-manual-2.md:274, a5-prep-and-safety-rev7.md:262] */
        attribute part_number : String = "Not stated";
        doc /* [unit: W] [Source: a5-user-manual-2.md:274, a5-prep-and-safety-rev7.md:262] */
        attribute power : String = "Not stated";
    }
    doc /* [Source: avenger_v2_5_sysml_v2_ingestion.md:43] */
    part def Proximity_Sensor {
        doc /* [Source: avenger_v2_5_sysml_v2_ingestion.md:43] */
        attribute component_name : String = "Impact and proximity trigger sensor";
        doc /* [Source: avenger_v2_5_sysml_v2_ingestion.md:43] */
        attribute interface_item : String = "Discrete trigger to ESAD; sensor board powered from ESAD";
        doc /* [unit: kg] [Source: avenger_v2_5_sysml_v2_ingestion.md:43] */
        attribute mass : String = "Not stated";
        doc /* [Source: avenger_v2_5_sysml_v2_ingestion.md:43] */
        attribute part_number : String = "Not stated";
        doc /* [unit: W] [Source: avenger_v2_5_sysml_v2_ingestion.md:43] */
        attribute power : String = "Not stated";
    }
    doc /* [Source: avenger_v2_5_sysml_v2_ingestion.md:12, avenger_v2_5_sysml_v2_ingestion.md:147] */
    part def RPI_CM5004032 {
        doc /* [Source: avenger_v2_5_sysml_v2_ingestion.md:12, avenger_v2_5_sysml_v2_ingestion.md:147] */
        attribute component_name : String = "Raspberry Pi compute module for SC2 command and control interfacing";
        doc /* [Source: avenger_v2_5_sysml_v2_ingestion.md:12, avenger_v2_5_sysml_v2_ingestion.md:147] */
        attribute interface_item : String = "ETH; serial to autopilot; RS-485 to ESAD; GPIO trigger to ESAD";
        doc /* [unit: kg] [Source: avenger_v2_5_sysml_v2_ingestion.md:12, avenger_v2_5_sysml_v2_ingestion.md:147] */
        attribute mass : String = "Not stated";
        doc /* [Source: avenger_v2_5_sysml_v2_ingestion.md:12, avenger_v2_5_sysml_v2_ingestion.md:147] */
        attribute part_number : String = "CM5004032";
        doc /* [unit: W] [Source: avenger_v2_5_sysml_v2_ingestion.md:12, avenger_v2_5_sysml_v2_ingestion.md:147] */
        attribute power : String = "Not stated";
    }
    doc /* [Source: avenger_v2_5_sysml_v2_ingestion.md:39] */
    part def Radio_Antenna_MPSL4400_Lower {
        doc /* [Source: avenger_v2_5_sysml_v2_ingestion.md:39] */
        attribute component_name : String = "Lower radio antenna";
        doc /* [Source: avenger_v2_5_sysml_v2_ingestion.md:39] */
        attribute interface_item : String = "Coaxial RF feed from radio module";
        doc /* [unit: kg] [Source: avenger_v2_5_sysml_v2_ingestion.md:39] */
        attribute mass : String = "Not stated";
        doc /* [Source: avenger_v2_5_sysml_v2_ingestion.md:39] */
        attribute part_number : String = "MPSL4400";
        doc /* [unit: W] [Source: avenger_v2_5_sysml_v2_ingestion.md:39] */
        attribute power : String = "Not stated";
    }
    doc /* [Source: avenger_v2_5_sysml_v2_ingestion.md:38] */
    part def Radio_Antenna_MPSL4400_Upper {
        doc /* [Source: avenger_v2_5_sysml_v2_ingestion.md:38] */
        attribute component_name : String = "Upper radio antenna";
        doc /* [Source: avenger_v2_5_sysml_v2_ingestion.md:38] */
        attribute interface_item : String = "Coaxial RF feed from radio module";
        doc /* [unit: kg] [Source: avenger_v2_5_sysml_v2_ingestion.md:38] */
        attribute mass : String = "Not stated";
        doc /* [Source: avenger_v2_5_sysml_v2_ingestion.md:38] */
        attribute part_number : String = "MPSL4400";
        doc /* [unit: W] [Source: avenger_v2_5_sysml_v2_ingestion.md:38] */
        attribute power : String = "Not stated";
    }
    doc /* [Source: avenger_v2_5_sysml_v2_ingestion.md:37] */
    part def Radio_Module_DTC {
        doc /* [Source: avenger_v2_5_sysml_v2_ingestion.md:37] */
        attribute component_name : String = "Command and control radio transceiver";
        doc /* [Source: avenger_v2_5_sysml_v2_ingestion.md:37] */
        attribute interface_item : String = "ETH; serial from autopilot; 12 V radio power; two RF antenna feeds";
        doc /* [unit: kg] [Source: avenger_v2_5_sysml_v2_ingestion.md:37] */
        attribute mass : String = "Not stated";
        doc /* [Source: avenger_v2_5_sysml_v2_ingestion.md:37] */
        attribute part_number : String = "DTC 4.4-5 GHz";
        doc /* [unit: W] [Source: avenger_v2_5_sysml_v2_ingestion.md:37] */
        attribute power : String = "Not stated";
    }
    doc /* [Source: avenger_v2_5_sysml_v2_ingestion.md:21, a5-user-manual-2.md:273, a5-prep-and-safety-rev7.md:242] */
    part def Ruddervator {
        doc /* [Source: avenger_v2_5_sysml_v2_ingestion.md:21, a5-user-manual-2.md:273, a5-prep-and-safety-rev7.md:242] */
        attribute component_name : String = "Canonical tail control surface assembly, quantity 4; drawing synonym Fins; preparation synonym tail stabiliser";
        doc /* [Source: avenger_v2_5_sysml_v2_ingestion.md:21, a5-user-manual-2.md:273, a5-prep-and-safety-rev7.md:242] */
        attribute interface_item : String = "Four tail mounting shafts; control horns; threaded retaining pins; Servos #1 to #4 on CAN 1";
        doc /* [unit: kg] [Source: avenger_v2_5_sysml_v2_ingestion.md:21, a5-user-manual-2.md:273, a5-prep-and-safety-rev7.md:242] */
        attribute mass : String = "Not stated";
        doc /* [Source: avenger_v2_5_sysml_v2_ingestion.md:21, a5-user-manual-2.md:273, a5-prep-and-safety-rev7.md:242] */
        attribute part_number : String = "HV6160-DroneCAN servo set";
        doc /* [unit: W] [Source: avenger_v2_5_sysml_v2_ingestion.md:21, a5-user-manual-2.md:273, a5-prep-and-safety-rev7.md:242] */
        attribute power : String = "Not stated";
    }
    doc /* [Source: avenger_v2_5_sysml_v2_ingestion.md:22, avenger_v2_5_sysml_v2_ingestion.md:155] */
    part def Ruddervator_Servo_1 {
        doc /* [Source: avenger_v2_5_sysml_v2_ingestion.md:22, avenger_v2_5_sysml_v2_ingestion.md:155] */
        attribute component_name : String = "Left-up tail servo, HV6160-DroneCAN, pitch and yaw mixing";
        doc /* [Source: avenger_v2_5_sysml_v2_ingestion.md:22, avenger_v2_5_sysml_v2_ingestion.md:155] */
        attribute interface_item : String = "CAN 1 120 cm branch; Servo power 8 V";
        doc /* [unit: kg] [Source: avenger_v2_5_sysml_v2_ingestion.md:22, avenger_v2_5_sysml_v2_ingestion.md:155] */
        attribute mass : String = "Not stated";
        doc /* [Source: avenger_v2_5_sysml_v2_ingestion.md:22, avenger_v2_5_sysml_v2_ingestion.md:155] */
        attribute part_number : String = "HV6160-DroneCAN";
        doc /* [unit: W] [Source: avenger_v2_5_sysml_v2_ingestion.md:22, avenger_v2_5_sysml_v2_ingestion.md:155] */
        attribute power : String = "Not stated";
    }
    doc /* [Source: avenger_v2_5_sysml_v2_ingestion.md:23, avenger_v2_5_sysml_v2_ingestion.md:155] */
    part def Ruddervator_Servo_2 {
        doc /* [Source: avenger_v2_5_sysml_v2_ingestion.md:23, avenger_v2_5_sysml_v2_ingestion.md:155] */
        attribute component_name : String = "Right-up tail servo, HV6160-DroneCAN, pitch and yaw mixing";
        doc /* [Source: avenger_v2_5_sysml_v2_ingestion.md:23, avenger_v2_5_sysml_v2_ingestion.md:155] */
        attribute interface_item : String = "CAN 1 120 cm branch; Servo power 8 V";
        doc /* [unit: kg] [Source: avenger_v2_5_sysml_v2_ingestion.md:23, avenger_v2_5_sysml_v2_ingestion.md:155] */
        attribute mass : String = "Not stated";
        doc /* [Source: avenger_v2_5_sysml_v2_ingestion.md:23, avenger_v2_5_sysml_v2_ingestion.md:155] */
        attribute part_number : String = "HV6160-DroneCAN";
        doc /* [unit: W] [Source: avenger_v2_5_sysml_v2_ingestion.md:23, avenger_v2_5_sysml_v2_ingestion.md:155] */
        attribute power : String = "Not stated";
    }
    doc /* [Source: avenger_v2_5_sysml_v2_ingestion.md:24, avenger_v2_5_sysml_v2_ingestion.md:155] */
    part def Ruddervator_Servo_3 {
        doc /* [Source: avenger_v2_5_sysml_v2_ingestion.md:24, avenger_v2_5_sysml_v2_ingestion.md:155] */
        attribute component_name : String = "Right-down tail servo, HV6160-DroneCAN, pitch and yaw mixing";
        doc /* [Source: avenger_v2_5_sysml_v2_ingestion.md:24, avenger_v2_5_sysml_v2_ingestion.md:155] */
        attribute interface_item : String = "CAN 1 120 cm branch; Servo power 8 V";
        doc /* [unit: kg] [Source: avenger_v2_5_sysml_v2_ingestion.md:24, avenger_v2_5_sysml_v2_ingestion.md:155] */
        attribute mass : String = "Not stated";
        doc /* [Source: avenger_v2_5_sysml_v2_ingestion.md:24, avenger_v2_5_sysml_v2_ingestion.md:155] */
        attribute part_number : String = "HV6160-DroneCAN";
        doc /* [unit: W] [Source: avenger_v2_5_sysml_v2_ingestion.md:24, avenger_v2_5_sysml_v2_ingestion.md:155] */
        attribute power : String = "Not stated";
    }
    doc /* [Source: avenger_v2_5_sysml_v2_ingestion.md:25, avenger_v2_5_sysml_v2_ingestion.md:155] */
    part def Ruddervator_Servo_4 {
        doc /* [Source: avenger_v2_5_sysml_v2_ingestion.md:25, avenger_v2_5_sysml_v2_ingestion.md:155] */
        attribute component_name : String = "Left-down tail servo, HV6160-DroneCAN, pitch and yaw mixing";
        doc /* [Source: avenger_v2_5_sysml_v2_ingestion.md:25, avenger_v2_5_sysml_v2_ingestion.md:155] */
        attribute interface_item : String = "CAN 1 120 cm branch; Servo power 8 V";
        doc /* [unit: kg] [Source: avenger_v2_5_sysml_v2_ingestion.md:25, avenger_v2_5_sysml_v2_ingestion.md:155] */
        attribute mass : String = "Not stated";
        doc /* [Source: avenger_v2_5_sysml_v2_ingestion.md:25, avenger_v2_5_sysml_v2_ingestion.md:155] */
        attribute part_number : String = "HV6160-DroneCAN";
        doc /* [unit: W] [Source: avenger_v2_5_sysml_v2_ingestion.md:25, avenger_v2_5_sysml_v2_ingestion.md:155] */
        attribute power : String = "Not stated";
    }
    doc /* [Source: a5-user-manual-2.md:340, a5-prep-and-safety-rev7.md:321] */
    part def Safety_RBF_Devices {
        doc /* [Source: a5-user-manual-2.md:340, a5-prep-and-safety-rev7.md:321] */
        attribute component_name : String = "Remove Before Flight flags, pitot cover, sensor cover, gimbal strap, power RBF and warhead RBF number 3";
        doc /* [Source: a5-user-manual-2.md:340, a5-prep-and-safety-rev7.md:321] */
        attribute interface_item : String = "Mechanical and electrical safety interlocks";
        doc /* [unit: kg] [Source: a5-user-manual-2.md:340, a5-prep-and-safety-rev7.md:321] */
        attribute mass : String = "Not stated";
        doc /* [Source: a5-user-manual-2.md:340, a5-prep-and-safety-rev7.md:321] */
        attribute part_number : String = "Not stated";
        doc /* [unit: W] [Source: a5-user-manual-2.md:340, a5-prep-and-safety-rev7.md:321] */
        attribute power : String = "Not stated";
    }
    doc /* [Source: a5-user-manual-2.md:366, a5-user-manual-2.md:367] */
    part def Support_Spare_Propeller {
        doc /* [Source: a5-user-manual-2.md:366, a5-user-manual-2.md:367] */
        attribute component_name : String = "Spare propeller blades, quantity 2, and propeller assembly, quantity 1";
        doc /* [Source: a5-user-manual-2.md:366, a5-user-manual-2.md:367] */
        attribute interface_item : String = "Propeller assembly";
        doc /* [unit: kg] [Source: a5-user-manual-2.md:366, a5-user-manual-2.md:367] */
        attribute mass : String = "Not stated";
        doc /* [Source: a5-user-manual-2.md:366, a5-user-manual-2.md:367] */
        attribute part_number : String = "Not stated";
        doc /* [unit: W] [Source: a5-user-manual-2.md:366, a5-user-manual-2.md:367] */
        attribute power : String = "Not stated";
    }
    doc /* [Source: a5-user-manual-2.md:365, a5-user-manual-2.md:368] */
    part def Support_Tools {
        doc /* [Source: a5-user-manual-2.md:365, a5-user-manual-2.md:368] */
        attribute component_name : String = "Set of tools and 30 spare attachment bolts";
        doc /* [Source: a5-user-manual-2.md:365, a5-user-manual-2.md:368] */
        attribute interface_item : String = "Maintenance";
        doc /* [unit: kg] [Source: a5-user-manual-2.md:365, a5-user-manual-2.md:368] */
        attribute mass : String = "Not stated";
        doc /* [Source: a5-user-manual-2.md:365, a5-user-manual-2.md:368] */
        attribute part_number : String = "Not stated";
        doc /* [unit: W] [Source: a5-user-manual-2.md:365, a5-user-manual-2.md:368] */
        attribute power : String = "Not stated";
    }
    doc /* [Source: avenger_v2_5_sysml_v2_ingestion.md:48] */
    part def UAV_RBF_Key {
        doc /* [Source: avenger_v2_5_sysml_v2_ingestion.md:48] */
        attribute component_name : String = "UAV power Remove Before Flight key";
        doc /* [Source: avenger_v2_5_sysml_v2_ingestion.md:48] */
        attribute interface_item : String = "Power meter ON/OFF interlock";
        doc /* [unit: kg] [Source: avenger_v2_5_sysml_v2_ingestion.md:48] */
        attribute mass : String = "Not stated";
        doc /* [Source: avenger_v2_5_sysml_v2_ingestion.md:48] */
        attribute part_number : String = "Not stated";
        doc /* [unit: W] [Source: avenger_v2_5_sysml_v2_ingestion.md:48] */
        attribute power : String = "Not stated";
    }
    doc /* [Source: avenger-5-spec-sheet-rev3.md:31, avenger-5-spec-sheet-rev3.md:133, a5-prep-and-safety-rev7.md:112] */
    part def Warhead {
        doc /* [Source: avenger-5-spec-sheet-rev3.md:31, avenger-5-spec-sheet-rev3.md:133, a5-prep-and-safety-rev7.md:112] */
        attribute component_name : String = "Modular warhead with HE, HEAT and thermobaric options";
        doc /* [Source: avenger-5-spec-sheet-rev3.md:31, avenger-5-spec-sheet-rev3.md:133, a5-prep-and-safety-rev7.md:112] */
        attribute interface_item : String = "ESAD payload cable; 1.5 mm HEX screw terminals; mounting brackets and retaining rings";
        doc /* [unit: kg] [Source: avenger-5-spec-sheet-rev3.md:31, avenger-5-spec-sheet-rev3.md:133, a5-prep-and-safety-rev7.md:112] */
        attribute mass : Integer = 5;
        doc /* [Source: avenger-5-spec-sheet-rev3.md:31, avenger-5-spec-sheet-rev3.md:133, a5-prep-and-safety-rev7.md:112] */
        attribute part_number : String = "UDS 5 kg warhead";
        doc /* [unit: W] [Source: avenger-5-spec-sheet-rev3.md:31, avenger-5-spec-sheet-rev3.md:133, a5-prep-and-safety-rev7.md:112] */
        attribute power : String = "Not stated";
    }
    doc /* [Source: a5-user-manual-2.md:272, a5-user-manual-2.md:337] */
    part def Wing_Panel_Left_Lower {
        doc /* [Source: a5-user-manual-2.md:272, a5-user-manual-2.md:337] */
        attribute component_name : String = "Left lower wing panel";
        doc /* [Source: a5-user-manual-2.md:272, a5-user-manual-2.md:337] */
        attribute interface_item : String = "Wing mounting bracket; M6 x 30 mm bolts; RF cable routing around hinge";
        doc /* [unit: kg] [Source: a5-user-manual-2.md:272, a5-user-manual-2.md:337] */
        attribute mass : String = "Not stated";
        doc /* [Source: a5-user-manual-2.md:272, a5-user-manual-2.md:337] */
        attribute part_number : String = "Not stated";
        doc /* [unit: W] [Source: a5-user-manual-2.md:272, a5-user-manual-2.md:337] */
        attribute power : String = "Not stated";
    }
    doc /* [Source: a5-user-manual-2.md:272, a5-user-manual-2.md:337] */
    part def Wing_Panel_Left_Upper {
        doc /* [Source: a5-user-manual-2.md:272, a5-user-manual-2.md:337] */
        attribute component_name : String = "Left upper wing panel";
        doc /* [Source: a5-user-manual-2.md:272, a5-user-manual-2.md:337] */
        attribute interface_item : String = "Wing mounting bracket; M6 x 30 mm bolts; RF cable routing around hinge";
        doc /* [unit: kg] [Source: a5-user-manual-2.md:272, a5-user-manual-2.md:337] */
        attribute mass : String = "Not stated";
        doc /* [Source: a5-user-manual-2.md:272, a5-user-manual-2.md:337] */
        attribute part_number : String = "Not stated";
        doc /* [unit: W] [Source: a5-user-manual-2.md:272, a5-user-manual-2.md:337] */
        attribute power : String = "Not stated";
    }
    doc /* [Source: a5-user-manual-2.md:272, a5-user-manual-2.md:338] */
    part def Wing_Panel_Right_Lower {
        doc /* [Source: a5-user-manual-2.md:272, a5-user-manual-2.md:338] */
        attribute component_name : String = "Right lower wing panel";
        doc /* [Source: a5-user-manual-2.md:272, a5-user-manual-2.md:338] */
        attribute interface_item : String = "Wing mounting bracket; M6 x 30 mm bolts; RF cable routing around hinge";
        doc /* [unit: kg] [Source: a5-user-manual-2.md:272, a5-user-manual-2.md:338] */
        attribute mass : String = "Not stated";
        doc /* [Source: a5-user-manual-2.md:272, a5-user-manual-2.md:338] */
        attribute part_number : String = "Not stated";
        doc /* [unit: W] [Source: a5-user-manual-2.md:272, a5-user-manual-2.md:338] */
        attribute power : String = "Not stated";
    }
    doc /* [Source: a5-user-manual-2.md:272, a5-user-manual-2.md:338] */
    part def Wing_Panel_Right_Upper {
        doc /* [Source: a5-user-manual-2.md:272, a5-user-manual-2.md:338] */
        attribute component_name : String = "Right upper wing panel";
        doc /* [Source: a5-user-manual-2.md:272, a5-user-manual-2.md:338] */
        attribute interface_item : String = "Wing mounting bracket; M6 x 30 mm bolts; RF cable routing around hinge";
        doc /* [unit: kg] [Source: a5-user-manual-2.md:272, a5-user-manual-2.md:338] */
        attribute mass : String = "Not stated";
        doc /* [Source: a5-user-manual-2.md:272, a5-user-manual-2.md:338] */
        attribute part_number : String = "Not stated";
        doc /* [unit: W] [Source: a5-user-manual-2.md:272, a5-user-manual-2.md:338] */
        attribute power : String = "Not stated";
    }
    doc /* [Source: avenger_v2_5_sysml_v2_ingestion.md:28, avenger_v2_5_sysml_v2_ingestion.md:156] */
    part def Wing_Servo_5 {
        doc /* [Source: avenger_v2_5_sysml_v2_ingestion.md:28, avenger_v2_5_sysml_v2_ingestion.md:156] */
        attribute component_name : String = "Left-up wing servo, HV6160-DroneCAN, roll stabilization";
        doc /* [Source: avenger_v2_5_sysml_v2_ingestion.md:28, avenger_v2_5_sysml_v2_ingestion.md:156] */
        attribute interface_item : String = "CAN 2 series daisy chain through splitter PCB; Servo power 8 V";
        doc /* [unit: kg] [Source: avenger_v2_5_sysml_v2_ingestion.md:28, avenger_v2_5_sysml_v2_ingestion.md:156] */
        attribute mass : String = "Not stated";
        doc /* [Source: avenger_v2_5_sysml_v2_ingestion.md:28, avenger_v2_5_sysml_v2_ingestion.md:156] */
        attribute part_number : String = "HV6160-DroneCAN";
        doc /* [unit: W] [Source: avenger_v2_5_sysml_v2_ingestion.md:28, avenger_v2_5_sysml_v2_ingestion.md:156] */
        attribute power : String = "Not stated";
    }
    doc /* [Source: avenger_v2_5_sysml_v2_ingestion.md:29, avenger_v2_5_sysml_v2_ingestion.md:156] */
    part def Wing_Servo_6 {
        doc /* [Source: avenger_v2_5_sysml_v2_ingestion.md:29, avenger_v2_5_sysml_v2_ingestion.md:156] */
        attribute component_name : String = "Right-up wing servo, HV6160-DroneCAN, roll stabilization";
        doc /* [Source: avenger_v2_5_sysml_v2_ingestion.md:29, avenger_v2_5_sysml_v2_ingestion.md:156] */
        attribute interface_item : String = "CAN 2 series daisy chain through splitter PCB; Servo power 8 V";
        doc /* [unit: kg] [Source: avenger_v2_5_sysml_v2_ingestion.md:29, avenger_v2_5_sysml_v2_ingestion.md:156] */
        attribute mass : String = "Not stated";
        doc /* [Source: avenger_v2_5_sysml_v2_ingestion.md:29, avenger_v2_5_sysml_v2_ingestion.md:156] */
        attribute part_number : String = "HV6160-DroneCAN";
        doc /* [unit: W] [Source: avenger_v2_5_sysml_v2_ingestion.md:29, avenger_v2_5_sysml_v2_ingestion.md:156] */
        attribute power : String = "Not stated";
    }
    doc /* [Source: avenger_v2_5_sysml_v2_ingestion.md:30, avenger_v2_5_sysml_v2_ingestion.md:156] */
    part def Wing_Servo_7 {
        doc /* [Source: avenger_v2_5_sysml_v2_ingestion.md:30, avenger_v2_5_sysml_v2_ingestion.md:156] */
        attribute component_name : String = "Right-down wing servo, HV6160-DroneCAN, roll stabilization";
        doc /* [Source: avenger_v2_5_sysml_v2_ingestion.md:30, avenger_v2_5_sysml_v2_ingestion.md:156] */
        attribute interface_item : String = "CAN 2 series daisy chain through splitter PCB; Servo power 8 V";
        doc /* [unit: kg] [Source: avenger_v2_5_sysml_v2_ingestion.md:30, avenger_v2_5_sysml_v2_ingestion.md:156] */
        attribute mass : String = "Not stated";
        doc /* [Source: avenger_v2_5_sysml_v2_ingestion.md:30, avenger_v2_5_sysml_v2_ingestion.md:156] */
        attribute part_number : String = "HV6160-DroneCAN";
        doc /* [unit: W] [Source: avenger_v2_5_sysml_v2_ingestion.md:30, avenger_v2_5_sysml_v2_ingestion.md:156] */
        attribute power : String = "Not stated";
    }
    doc /* [Source: avenger_v2_5_sysml_v2_ingestion.md:31, avenger_v2_5_sysml_v2_ingestion.md:156] */
    part def Wing_Servo_8 {
        doc /* [Source: avenger_v2_5_sysml_v2_ingestion.md:31, avenger_v2_5_sysml_v2_ingestion.md:156] */
        attribute component_name : String = "Left-down wing servo, HV6160-DroneCAN, roll stabilization";
        doc /* [Source: avenger_v2_5_sysml_v2_ingestion.md:31, avenger_v2_5_sysml_v2_ingestion.md:156] */
        attribute interface_item : String = "CAN 2 series daisy chain through splitter PCB; Servo power 8 V";
        doc /* [unit: kg] [Source: avenger_v2_5_sysml_v2_ingestion.md:31, avenger_v2_5_sysml_v2_ingestion.md:156] */
        attribute mass : String = "Not stated";
        doc /* [Source: avenger_v2_5_sysml_v2_ingestion.md:31, avenger_v2_5_sysml_v2_ingestion.md:156] */
        attribute part_number : String = "HV6160-DroneCAN";
        doc /* [unit: W] [Source: avenger_v2_5_sysml_v2_ingestion.md:31, avenger_v2_5_sysml_v2_ingestion.md:156] */
        attribute power : String = "Not stated";
    }
    doc /* [Source: avenger_v2_5_sysml_v2_ingestion.md:27, avenger_v2_5_sysml_v2_ingestion.md:156] */
    part def Wings {
        doc /* [Source: avenger_v2_5_sysml_v2_ingestion.md:27, avenger_v2_5_sysml_v2_ingestion.md:156] */
        attribute component_name : String = "Wing assembly boundary with four wing panels and Servos #5 to #8";
        doc /* [Source: avenger_v2_5_sysml_v2_ingestion.md:27, avenger_v2_5_sysml_v2_ingestion.md:156] */
        attribute interface_item : String = "Wing mounting brackets; four panels; CAN 2 series chain; Servo power 8 V";
        doc /* [unit: kg] [Source: avenger_v2_5_sysml_v2_ingestion.md:27, avenger_v2_5_sysml_v2_ingestion.md:156] */
        attribute mass : String = "Not stated";
        doc /* [Source: avenger_v2_5_sysml_v2_ingestion.md:27, avenger_v2_5_sysml_v2_ingestion.md:156] */
        attribute part_number : String = "Not stated";
        doc /* [unit: W] [Source: avenger_v2_5_sysml_v2_ingestion.md:27, avenger_v2_5_sysml_v2_ingestion.md:156] */
        attribute power : String = "Not stated";
    }
}
